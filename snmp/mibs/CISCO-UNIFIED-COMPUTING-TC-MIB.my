-- *********************************************************************
-- CISCO-UNIFIED-COMPUTING-TC-MIB.my
-- 
-- MIB representation of the Cisco Unified Computing System
-- TEXTUALCONVENTIONS management information model package
-- 
-- Created December 2010 by Charles Bullis
-- 
-- Copyright (c) 2005-2010 Cisco Systems, Inc. All rights reserved.
-- 
-- *********************************************************************

CISCO-UNIFIED-COMPUTING-TC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIB,
    CucsManagedObjectId,
    CucsManagedObjectDn
        FROM CISCO-UNIFIED-COMPUTING-MIB;

cucsTextualConventionsObjects MODULE-IDENTITY
    LAST-UPDATED    "201004190000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        TEXTUALCONVENTIONS management information model package"
    ::= { ciscoUnifiedComputingMIB 4 }

CucsAaaAccess ::= TEXTUAL-CONVENTION
    STATUS        current
    DESCRIPTION
        ""
    SYNTAX        BITS {
        readOnly(0),
        admin(1),
        operations(2),
        fault(3),
        aaa(4),
        podConfig(5),
        podPolicy(6),
        podSecurity(7),
        podQos(8),
        extLanConfig(9),
        extLanPolicy(10),
        extLanSecurity(11),
        extLanQos(12),
        extSanConfig(13),
        extSanPolicy(14),
        extSanSecurity(15),
        extSanQos(16),
        pnEquipment(17),
        pnPolicy(18),
        pnSecurity(19),
        pnMaintenance(20),
        lsConfig(21),
        lsStorage(22),
        lsNetwork(23),
        lsSecurity(24),
        lsServer(25),
        lsQos(26),
        lsConfigPolicy(27),
        lsStoragePolicy(28),
        lsNetworkPolicy(29),
        lsSecurityPolicy(30),
        lsServerPolicy(31),
        lsQosPolicy(32),
        lsExtAccess(33),
        powerMgmt(34),
        lsServerOper(36)
    }

CucsAaaAccountStatus ::= TEXTUAL-CONVENTION
    STATUS        current
    DESCRIPTION
        ""
    SYNTAX        INTEGER {
        active(0),
        inactive(1)
    }

CucsAaaDomainAuthRealm ::= TEXTUAL-CONVENTION
    STATUS        current
    DESCRIPTION
        ""
    SYNTAX        INTEGER {
        local(0),
        radius(1),
        tacacs(2),
        ldap(3),
        none(4)
    }

CucsAaaEpAccess ::= TEXTUAL-CONVENTION
    STATUS        current
    DESCRIPTION
        ""
    SYNTAX        INTEGER {
        readonly(1),
        admin(2)
    }

CucsAaaEpFsmTaskItem ::= TEXTUAL-CONVENTION
    STATUS        current
    DESCRIPTION
        ""
    SYNTAX        INTEGER {
        nop(0),
        updateEp(197)
    }

CucsAaaExtMgmtAccess ::= TEXTUAL-CONVENTION
    STATUS        current
    DESCRIPTION
        ""
    SYNTAX        INTEGER {
        kvm(1)
    }

CucsAaaLdapGroupRuleAuthorization ::= TEXTUAL-CONVENTION
    STATUS        current
    DESCRIPTION
        ""
    SYNTAX        INTEGER {
        disable(0),
        enable(1)
    }

CucsAaaLdapGroupRuleTraversal ::= TEXTUAL-CONVENTION
    STATUS        current
    DESCRIPTION
        ""
    SYNTAX        INTEGER {
        nonRecursive(0),
        recursive(1)
    }

CucsAaaNoRolePolicy ::= TEXTUAL-CONVENTION
    STATUS        current
    DESCRIPTION
        ""
    SYNTAX        INTEGER {
        noLogin(0),
        assignDefaultRole(1)
    }

CucsAaaRadiusService ::= TEXTUAL-CONVENTION
    STATUS        current
    DESCRIPTION
        ""
    SYNTAX        INTEGER {
        all(0),
        defaultValue(1),
        accounting(2)
    }

CucsAaaRealm ::= TEXTUAL-CONVENTION
    STATUS        current
    DESCRIPTION
        ""
    SYNTAX        INTEGER {
        local(0),
        radius(1),
        tacacs(2),
        ldap(3),
        none(4)
    }

CucsAaaRealmFsmTaskItem ::= TEXTUAL-CONVENTION
    STATUS        current
    DESCRIPTION
        ""
    SYNTAX        INTEGER {
        nop(0),
        updateRealm(200)
    }

CucsAaaSession ::= TEXTUAL-CONVENTION
    STATUS        current
    DESCRIPTION
        ""
    SYNTAX        INTEGER {
        local(0),
        remote(1)
    }

CucsAaaSshStr ::= TEXTUAL-CONVENTION
    STATUS        current
    DESCRIPTION
        ""
    SYNTAX        INTEGER {
        none(0),
        key(1)
    }

CucsAaaUserEpFsmTaskItem ::= TEXTUAL-CONVENTION
    STATUS        current
    DESCRIPTION
        ""
    SYNTAX        INTEGER {
        nop(0),
        updateUserEp(203)
    }

CucsAaaUserInterface ::= TEXTUAL-CONVENTION
    STATUS        current
    DESCRIPTION
        ""
    SYNTAX        INTEGER {
        none(0),
        shell(1),
        web(2),
        ep(3)
    }

CucsAdaptorAdapterStatsTrafficDir ::= TEXTUAL-CONVENTION
    STATUS        current
    DESCRIPTION
        ""
    SYNTAX        INTEGER {
        unknown(0),
        tx(1),
        rx(2)
    }

CucsAdaptorCapDefType ::= TEXTUAL-CONVENTION
    STATUS        current
    DESCRIPTION
        ""
    SYNTAX        INTEGER {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11)
    }

CucsAdaptorCapSpecType ::= TEXTUAL-CONVENTION
    STATUS        current
    DESCRIPTION
        ""
    SYNTAX        INTEGER {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11)
    }

CucsAdaptorDefaultAction ::= TEXTUAL-CONVENTION
    STATUS        current
    DESCRIPTION
        ""
    SYNTAX        INTEGER {
        no(0),
        yes(1)
    }

CucsAdaptorEthInterruptProfileCoalescingType ::= TEXTUAL-CONVENTION
    STATUS        current
    DESCRIPTION
        ""
    SYNTAX        INTEGER {
        min(0),
        idle(1)
    }

CucsAdaptorEthOffloadProfileLargeReceive ::= TEXTUAL-CONVENTION
    STATUS        current
    DESCRIPTION
        ""
    SYNTAX        INTEGER {
        disabled(0),
        enabled(1)
    }

CucsAdaptorEthOffloadProfileTcpRxChecksum ::= TEXTUAL-CONVENTION
    STATUS        current
    DESCRIPTION
        ""
    SYNTAX        INTEGER {
        disabled(0),
        enabled(1)
    }

CucsAdaptorEthOffloadProfileTcpSegment ::= TEXTUAL-CONVENTION
    STATUS        current
    DESCRIPTION
        ""
    SYNTAX        INTEGER {
        disabled(0),
        enabled(1)
    }

CucsAdaptorEthOffloadProfileTcpTxChecksum ::= TEXTUAL-CONVENTION
    STATUS        current
    DESCRIPTION
        ""
    SYNTAX        INTEGER {
        disabled(0),
        enabled(1)
    }

CucsAdaptorEthPortBySizeLargeStatsThresholded ::= TEXTUAL-CONVENTION
    STATUS        current
    DESCRIPTION
        ""
    SYNTAX        BITS {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CucsAdaptorEthPortBySizeLargeStatsHistThresholded ::= TEXTUAL-CONVENTION
    STATUS        current
    DESCRIPTION
        ""
    SYNTAX        BITS {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CucsAdaptorEthPortBySizeSmallStatsThresholded ::= TEXTUAL-CONVENTION
    STATUS        current
    DESCRIPTION
        ""
    SYNTAX        BITS {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CucsAdaptorEthPortBySizeSmallStatsHistThresholded ::= TEXTUAL-CONVENTION
    STATUS        current
    DESCRIPTION
        ""
    SYNTAX        BITS {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CucsAdaptorEthPortErrStatsThresholded ::= TEXTUAL-CONVENTION
    STATUS        current
    DESCRIPTION
        ""
    SYNTAX        BITS {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11)
    }

CucsAdaptorEthPortErrStatsHistThresholded ::= TEXTUAL-CONVENTION
    STATUS        current
    DESCRIPTION
        ""
    SYNTAX        BITS {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11)
    }

CucsAdaptorEthPortMcastStatsThresholded ::= TEXTUAL-CONVENTION
    STATUS        current
    DESCRIPTION
        ""
    SYNTAX        BITS {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CucsAdaptorEthPortMcastStatsHistThresholded ::= TEXTUAL-CONVENTION
    STATUS        current
    DESCRIPTION
        ""
    SYNTAX        BITS {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CucsAdaptorEthPortOutsizedStatsThresholded ::= TEXTUAL-CONVENTION
    STATUS        current
    DESCRIPTION
        ""
    SYNTAX        BITS {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CucsAdaptorEthPortOutsizedStatsHistThresholded ::= TEXTUAL-CONVENTION
    STATUS        current
    DESCRIPTION
        ""
    SYNTAX        BITS {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CucsAdaptorEthPortStatsThresholded ::= TEXTUAL-CONVENTION
    STATUS        current
    DESCRIPTION
        ""
    SYNTAX        BITS {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CucsAdaptorEthPortStatsHistThresholded ::= TEXTUAL-CONVENTION
    STATUS        current
    DESCRIPTION
        ""
    SYNTAX        BITS {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CucsAdaptorEtherIfStatsThresholded ::= TEXTUAL-CONVENTION
    STATUS        current
    DESCRIPTION
        ""
    SYNTAX        BITS {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CucsAdaptorEtherIfStatsHistThresholded ::= TEXTUAL-CONVENTION
    STATUS        current
    DESCRIPTION
        ""
    SYNTAX        BITS {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CucsAdaptorExtEthIfFsmTaskItem ::= TEXTUAL-CONVENTION
    STATUS        current
    DESCRIPTION
        ""
    SYNTAX        INTEGER {
        nop(0),
        pathReset(499)
    }

CucsAdaptorExtIfAdminState ::= TEXTUAL-CONVENTION
    STATUS        current
    DESCRIPTION
        ""
    SYNTAX        INTEGER {
        enabled(0),
        resetConnectivity(44)
    }

CucsAdaptorExtIpV6RssHashProfileIpHash ::= TEXTUAL-CONVENTION
    STATUS        current
    DESCRIPTION
        ""
    SYNTAX        INTEGER {
        disabled(0),
        enabled(1)
    }

CucsAdaptorExtIpV6RssHashProfileTcpHash ::= TEXTUAL-CONVENTION
    STATUS        current
    DESCRIPTION
        ""
    SYNTAX        INTEGER {
        disabled(0),
        enabled(1)
    }

CucsAdaptorFcErrorRecoveryProfileFcpErrorRecovery ::= TEXTUAL-CONVENTION
    STATUS        current
    DESCRIPTION
        ""
    SYNTAX        INTEGER {
        disabled(0),
        enabled(1)
    }

CucsAdaptorFcIfEventStatsThresholded ::= TEXTUAL-CONVENTION
    STATUS        current
    DESCRIPTION
        ""
    SYNTAX        BITS {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CucsAdaptorFcIfEventStatsHistThresholded ::= TEXTUAL-CONVENTION
    STATUS        current
    DESCRIPTION
        ""
    SYNTAX        BITS {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CucsAdaptorFcIfFC4StatsThresholded ::= TEXTUAL-CONVENTION
    STATUS        current
    DESCRIPTION
        ""
    SYNTAX        BITS {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CucsAdaptorFcIfFC4StatsHistThresholded ::= TEXTUAL-CONVENTION
    STATUS        current
    DESCRIPTION
        ""
    SYNTAX        BITS {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CucsAdaptorFcIfFrameStatsThresholded ::= TEXTUAL-CONVENTION
    STATUS        current
    DESCRIPTION
        ""
    SYNTAX        BITS {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CucsAdaptorFcIfFrameStatsHistThresholded ::= TEXTUAL-CONVENTION
    STATUS        current
    DESCRIPTION
        ""
    SYNTAX        BITS {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CucsAdaptorFcPortStatsThresholded ::= TEXTUAL-CONVENTION
    STATUS        current
    DESCRIPTION
        ""
    SYNTAX        BITS {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CucsAdaptorFcPortStatsHistThresholded ::= TEXTUAL-CONVENTION
    STATUS        current
    DESCRIPTION
        ""
    SYNTAX        BITS {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CucsAdaptorHostEthIfFsmTaskItem ::= TEXTUAL-CONVENTION
    STATUS        current
    DESCRIPTION
        ""
    SYNTAX        INTEGER {
        nop(0),
        circuitReset(505)
    }

CucsAdaptorHostFcIfAdminState ::= TEXTUAL-CONVENTION
    STATUS        current
    DESCRIPTION
        ""
    SYNTAX        INTEGER {
        enabled(0),
        resetConnectivityActive(44),
        resetConnectivityPassive(45),
        resetConnectivity(46)
    }

CucsAdaptorHostFcIfPersBind ::= TEXTUAL-CONVENTION
    STATUS        current
    DESCRIPTION
        ""
    SYNTAX        INTEGER {
        disabled(0),
        enabled(4)
    }

CucsAdaptorHostFcIfFsmTaskItem ::= TEXTUAL-CONVENTION
    STATUS        current
    DESCRIPTION
        ""
    SYNTAX        INTEGER {
        nop(0),
        resetFcPersBinding(142),
        circuitReset(510)
    }

CucsAdaptorHostIfAdminState ::= TEXTUAL-CONVENTION
    STATUS        current
    DESCRIPTION
        ""
    SYNTAX        INTEGER {
        enabled(0),
        resetConnectivityActive(44),
        resetConnectivityPassive(45),
        resetConnectivity(46)
    }

CucsAdaptorHostIfBootDev ::= TEXTUAL-CONVENTION
    STATUS        current
    DESCRIPTION
        ""
    SYNTAX        INTEGER {
        disabled(0),
        enabled(1)
    }

CucsAdaptorHostMgmtCapPreboot ::= TEXTUAL-CONVENTION
    STATUS        current
    DESCRIPTION
        ""
    SYNTAX        INTEGER {
        none(0),
        pnuOS(1),
        efi(2)
    }

CucsAdaptorInterruptMode ::= TEXTUAL-CONVENTION
    STATUS        current
    DESCRIPTION
        ""
    SYNTAX        INTEGER {
        msiX(1),
        msi(2),
        intx(3)
    }

CucsAdaptorIpV4RssHashProfileIpHash ::= TEXTUAL-CONVENTION
    STATUS        current
    DESCRIPTION
        ""
    SYNTAX        INTEGER {
        disabled(0),
        enabled(1)
    }

CucsAdaptorIpV4RssHashProfileTcpHash ::= TEXTUAL-CONVENTION
    STATUS        current
    DESCRIPTION
        ""
    SYNTAX        INTEGER {
        disabled(0),
        enabled(1)
    }

CucsAdaptorIpV6RssHashProfileIpHash ::= TEXTUAL-CONVENTION
    STATUS        current
    DESCRIPTION
        ""
    SYNTAX        INTEGER {
        disabled(0),
        enabled(1)
    }

CucsAdaptorIpV6RssHashProfileTcpHash ::= TEXTUAL-CONVENTION
    STATUS        current
    DESCRIPTION
        ""
    SYNTAX        INTEGER {
        disabled(0),
        enabled(1)
    }

CucsAdaptorLanCapDefaultVlan ::= TEXTUAL-CONVENTION
    STATUS        current
    DESCRIPTION
        ""
    SYNTAX        INTEGER {
        nativeVlan(1),
        defaultVlan(2)
    }

CucsAdaptorLinkState ::= TEXTUAL-CONVENTION
    STATUS        current
    DESCRIPTION
        ""
    SYNTAX        INTEGER {
        unknown(0),
        adminDown(1),
        down(2),
        error(3),
        up(4),
        unallocated(5)
    }

CucsAdaptorLldpCapSupport ::= TEXTUAL-CONVENTION
    STATUS        current
    DESCRIPTION
        ""
    SYNTAX        INTEGER {
        none(1),
        full(2)
    }

CucsAdaptorMenloBaseErrorStatsThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CucsAdaptorMenloBaseErrorStatsHistThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CucsAdaptorMenloDcePortStatsThresholded ::= TEXTUAL-CONVENTION
    STATUS        current
    DESCRIPTION
        ""
    SYNTAX        BITS {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloDcePortStatsHistThresholded ::= TEXTUAL-CONVENTION
    STATUS        current
    DESCRIPTION
        ""
    SYNTAX        BITS {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloEthErrorStatsThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CucsAdaptorMenloEthErrorStatsHistThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CucsAdaptorMenloEthStatsThresholded ::= TEXTUAL-CONVENTION
    STATUS        current
    DESCRIPTION
        ""
    SYNTAX        BITS {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CucsAdaptorMenloEthStatsHistThresholded ::= TEXTUAL-CONVENTION
    STATUS        current
    DESCRIPTION
        ""
    SYNTAX        BITS {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CucsAdaptorMenloFcErrorStatsThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloFcErrorStatsHistThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloFcStatsThresholded ::= TEXTUAL-CONVENTION
    STATUS        current
    DESCRIPTION
        ""
    SYNTAX        BITS {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloFcStatsHistThresholded ::= TEXTUAL-CONVENTION
    STATUS        current
    DESCRIPTION
        ""
    SYNTAX        BITS {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloHostPortStatsThresholded ::= TEXTUAL-CONVENTION
    STATUS        current
    DESCRIPTION
        ""
    SYNTAX        BITS {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloHostPortStatsHistThresholded ::= TEXTUAL-CONVENTION
    STATUS        current
    DESCRIPTION
        ""
    SYNTAX        BITS {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CucsAdaptorMenloMcpuErrorStatsThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloMcpuErrorStatsHistThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloMcpuStatsThresholded ::= TEXTUAL-CONVENTION
    STATUS        current
    DESCRIPTION
        ""
    SYNTAX        BITS {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloMcpuStatsHistThresholded ::= TEXTUAL-CONVENTION
    STATUS        current
    DESCRIPTION
        ""
    SYNTAX        BITS {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CucsAdaptorMenloNetEgStatsThresholded ::= TEXTUAL-CONVENTION
    STATUS        current
    DESCRIPTION
        ""
    SYNTAX        BITS {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CucsAdaptorMenloNetEgStatsHistThresholded ::= TEXTUAL-CONVENTION
    STATUS        current
    DESCRIPTION
        ""
    SYNTAX        BITS {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CucsAdaptorMenloNetInStatsThresholded ::= TEXTUAL-CONVENTION
    STATUS        current
    DESCRIPTION
        ""
    SYNTAX        BITS {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CucsAdaptorMenloNetInStatsHistThresholded ::= TEXTUAL-CONVENTION
    STATUS        current
    DESCRIPTION
        ""
    SYNTAX        BITS {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CucsAdaptorMenloQErrorStatsThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloQErrorStatsHistThresholded ::= TEXTUAL-CONVENTION
    STATUS        current
    DESCRIPTION
        ""
    SYNTAX        BITS {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CucsAdaptorMenloQStatsThresholded ::= TEXTUAL-CONVENTION
    STATUS        current
    DESCRIPTION
        ""
    SYNTAX        BITS {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CucsAdaptorMenloQStatsHistThresholded ::= TEXTUAL-CONVENTION
    STATUS        current
    DESCRIPTION
        ""
    SYNTAX        BITS {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CucsAdaptorMenloQueueStatsComponent ::= TEXTUAL-CONVENTION
    STATUS        current
    DESCRIPTION
        ""
    SYNTAX        INTEGER {
        unknown(0),
        cpu(1),
        eth(2),
        fc(3),
        n(4)
    }

CucsAdaptorMenloStatsIndex ::= TEXTUAL-CONVENTION
    STATUS        current
    DESCRIPTION
        ""
    SYNTAX        INTEGER {
        unknown(0),
        n0(1),
        n1(2),
        n0A(3),
        n0B(4),
        n1A(5),
        n1B(6)
    }

CucsAdaptorMgmtCapMode ::= TEXTUAL-CONVENTION
    STATUS        current
    DESCRIPTION
        ""
    SYNTAX        INTEGER {
        full(1),
        partial(2)
    }

CucsAdaptorMgmtCapOperPowerRequirement ::= TEXTUAL-CONVENTION
    STATUS        current
    DESCRIPTION
        ""
    SYNTAX        INTEGER {
        none(0),
        standby(1),
        full(2)
    }

CucsAdaptorMgmtCapRebootActionOnDestructive ::= TEXTUAL-CONVENTION
    STATUS        current
    DESCRIPTION
        ""
    SYNTAX        INTEGER {
        none(0),
        host(1),
        adaptor(2)
    }

CucsAdaptorNwMgmtCapApi ::= TEXTUAL-CONVENTION
    STATUS        current
    DESCRIPTION
        ""
    SYNTAX        INTEGER {
        none(0),
        menlo(1),
        palo(2)
    }

CucsAdaptorNwMgmtCapMgmtTransport ::= TEXTUAL-CONVENTION
    STATUS        current
    DESCRIPTION
        ""
    SYNTAX        INTEGER {
        l2(0),
        l3(1)
    }

CucsAdaptorPurpose ::= TEXTUAL-CONVENTION
    STATUS        current
    DESCRIPTION
        ""
    SYNTAX        INTEGER {
        unused(0),
        general(1),
        management(2),
        utility(3)
    }

CucsAdaptorReachability ::= TEXTUAL-CONVENTION
    STATUS        current
    DESCRIPTION
        ""
    SYNTAX        BITS {
        a(0),
        b(1),
        unmanaged(7)
    }

CucsAdaptorRssProfileReceiveSideScaling ::= TEXTUAL-CONVENTION
    STATUS        current
    DESCRIPTION
        ""
    SYNTAX        INTEGER {
        disabled(0),
        enabled(1)
    }

CucsAdaptorSanCapHostNvram ::= TEXTUAL-CONVENTION
    STATUS        current
    DESCRIPTION
        ""
    SYNTAX        INTEGER {
        none(1),
        full(2)
    }

CucsAdaptorUnitId ::= TEXTUAL-CONVENTION
    STATUS        current
    DESCRIPTION
        ""
    SYNTAX        Gauge32 (1..8)

CucsAdaptorVnicStatsThresholded ::= TEXTUAL-CONVENTION
    STATUS        current
    DESCRIPTION
        ""
    SYNTAX        BITS {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAdaptorVnicStatsHistThresholded ::= TEXTUAL-CONVENTION
    STATUS        current
    DESCRIPTION
        ""
    SYNTAX        BITS {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CucsAddressMACMask ::= TEXTUAL-CONVENTION
    STATUS        current
    DESCRIPTION
        ""
    SYNTAX        Counter64 {
        fxxxxxxxxxxx(263882790666240),
        ffxxxxxxxxxx(280375465082880),
        fffxxxxxxxxx(281406257233920),
        ffffxxxxxxxx(281470681743360),
        fffffxxxxxxx(281474708275200),
        ffffffxxxxxx(281474959933440),
        fffffffxxxxx(281474975662080),
        ffffffffxxxx(281474976645120),
        fffffffffxxx(281474976706560),
        ffffffffffxx(281474976710400),
        fffffffffffx(281474976710640)
    }

CucsAddressUIDSuffxMask ::= TEXTUAL-CONVENTION
    STATUS        current
    DESCRIPTION
        ""
    SYNTAX        Counter64 {
        xxxxxxxxxxxxxxxx(0),
        fxxxxxxxxxxxxxxx(17293822569102704640),
        ffxxxxxxxxxxxxxx(18374686479671623680),
        fffxxxxxxxxxxxxx(18442240474082181120),
        ffffxxxxxxxxxxxx(18446462598732840960),
        fffffxxxxxxxxxxx(18446726481523507200),
        ffffffxxxxxxxxxx(18446742974197923840),
        fffffffxxxxxxxxx(18446744004990074880),
        ffffffffxxxxxxxx(18446744069414584320),
        fffffffffxxxxxxx(18446744073441116160),
        ffffffffffxxxxxx(18446744073692774400),
        fffffffffffxxxxx(18446744073708503040),
        ffffffffffffxxxx(18446744073709486080),
        fffffffffffffxxx(18446744073709547520),
        ffffffffffffffxx(18446744073709551360),
        fffffffffffffffx(18446744073709551600)
    }

CucsAddressWWNMask ::= TEXTUAL-CONVENTION
    STATUS        current
    DESCRIPTION
        ""
    SYNTAX        Counter64 {
        fxxxxxxxxxxxxxxx(17293822569102704640),
        ffxxxxxxxxxxxxxx(18374686479671623680),
        fffxxxxxxxxxxxxx(18442240474082181120),
        ffffxxxxxxxxxxxx(18446462598732840960),
        fffffxxxxxxxxxxx(18446726481523507200),
        ffffffxxxxxxxxxx(18446742974197923840),
        fffffffxxxxxxxxx(18446744004990074880),
        ffffffffxxxxxxxx(18446744069414584320),
        fffffffffxxxxxxx(18446744073441116160),
        ffffffffffxxxxxx(18446744073692774400),
        fffffffffffxxxxx(18446744073708503040),
        ffffffffffffxxxx(18446744073709486080),
        fffffffffffffxxx(18446744073709547520),
        ffffffffffffffxx(18446744073709551360),
        fffffffffffffffx(18446744073709551600)
    }

CucsBiosBootDevGrpType ::= TEXTUAL-CONVENTION
    STATUS        current
    DESCRIPTION
        ""
    SYNTAX        INTEGER {
        systemBootOrder(0),
        fddOrder(1),
        hddOrder(2),
        cdOrder(3),
        networkDeviceOrder(6),
        internalEfiShell(16),
        bevOrder(128)
    }

CucsBiosBootDevOrder ::= TEXTUAL-CONVENTION
    STATUS        current
    DESCRIPTION
        ""
    SYNTAX        INTEGER {
        n1(1),
        n2(2),
        n3(3),
        n4(4)
    }

CucsBiosDefaultAction ::= TEXTUAL-CONVENTION
    STATUS        current
    DESCRIPTION
        ""
    SYNTAX        INTEGER {
        no(0),
        yes(1)
    }

CucsBiosSupportedAction ::= TEXTUAL-CONVENTION
    STATUS        current
    DESCRIPTION
        ""
    SYNTAX        INTEGER {
        no(0),
        yes(1)
    }

CucsBiosVfACPI10SupportVpACPI10Support ::= TEXTUAL-CONVENTION
    STATUS        current
    DESCRIPTION
        ""
    SYNTAX        INTEGER {
        platformRecommended(0),
        disabled(122),
        enabled(123),
        platformDefault(4294967294)
    }

CucsBiosVfAssertNMIOnPERRVpAssertNMIOnPERR ::= TEXTUAL-CONVENTION
    STATUS        current
    DESCRIPTION
        ""
    SYNTAX        INTEGER {
        platformRecommended(0),
        disabled(68),
        enabled(69),
        platformDefault(4294967294)
    }

CucsBiosVfAssertNMIOnSERRVpAssertNMIOnSERR ::= TEXTUAL-CONVENTION
    STATUS        current
    DESCRIPTION
        ""
    SYNTAX        INTEGER {
        platformRecommended(0),
        disabled(66),
        enabled(67),
        platformDefault(4294967294)
    }

CucsBiosVfBootOptionRetryVpBootOptionRetry ::= TEXTUAL-CONVENTION
    STATUS        current
    DESCRIPTION
        ""
    SYNTAX        INTEGER {
        platformRecommended(0),
        disabled(96),
        enabled(97),
        platformDefault(4294967294)
    }

CucsBiosVfCPUPerformanceVpCPUPerformance ::= TEXTUAL-CONVENTION
    STATUS        current
    DESCRIPTION
        ""
    SYNTAX        INTEGER {
        platformRecommended(0),
        enterprise(175),
        highThroughput(176),
        hpc(177),
        platformDefault(4294967294)
    }

CucsBiosVfConsoleRedirectionVpBaudRate ::= TEXTUAL-CONVENTION
    STATUS        current
    DESCRIPTION
        ""
    SYNTAX        INTEGER {
        platformRecommended(0),
        n9600(81),
        n19200(82),
        n38400(83),
        n57600(84),
        n115200(85),
        platformDefault(4294967294)
    }

CucsBiosVfConsoleRedirectionVpConsoleRedirection ::= TEXTUAL-CONVENTION
    STATUS        current
    DESCRIPTION
        ""
    SYNTAX        INTEGER {
        platformRecommended(0),
        disabled(77),
        serialPortA(78),
        serialPortB(129),
        platformDefault(4294967294)
    }

CucsBiosVfConsoleRedirectionVpFlowControl ::= TEXTUAL-CONVENTION
    STATUS        current
    DESCRIPTION
        ""
    SYNTAX        INTEGER {
        platformRecommended(0),
        none(79),
        rtsCts(80),
        platformDefault(4294967294)
    }

CucsBiosVfConsoleRedirectionVpLegacyOSRedirection ::= TEXTUAL-CONVENTION
    STATUS        current
    DESCRIPTION
        ""
    SYNTAX        INTEGER {
        platformRecommended(0),
        disabled(90),
        enabled(91),
        platformDefault(4294967294)
    }

CucsBiosVfConsoleRedirectionVpTerminalType ::= TEXTUAL-CONVENTION
    STATUS        current
    DESCRIPTION
        ""
    SYNTAX        INTEGER {
        platformRecommended(0),
        pcAnsi(86),
        vt100(87),
        vt100Plus(88),
        vtUtf8(89),
        platformDefault(4294967294)
    }

CucsBiosVfCoreMultiProcessingVpCoreMultiProcessing ::= TEXTUAL-CONVENTION
    STATUS        current
    DESCRIPTION
        ""
    SYNTAX        INTEGER {
        platformRecommended(0),
        all(7),
        n1(178),
        n2(179),
        n3(180),
        n4(181),
        n5(182),
        n6(183),
        n7(184),
        n8(185),
        platformDefault(4294967294)
    }

CucsBiosVfDirectCacheAccessVpDirectCacheAccess ::= TEXTUAL-CONVENTION
    STATUS        current
    DESCRIPTION
        ""
    SYNTAX        INTEGER {
        platformRecommended(0),
        disabled(28),
        enabled(29),
        platformDefault(4294967294)
    }

CucsBiosVfEnhancedIntelSpeedStepTechVpEnhancedIntelSpeedStepTech ::= TEXTUAL-CONVENTION
    STATUS        current
    DESCRIPTION
        ""
    SYNTAX        INTEGER {
        platformRecommended(0),
        disabled(3),
        enabled(4),
        platformDefault(4294967294)
    }

CucsBiosVfExecuteDisableBitVpExecuteDisableBit ::= TEXTUAL-CONVENTION
    STATUS        current
    DESCRIPTION
        ""
    SYNTAX        INTEGER {
        platformRecommended(0),
        disabled(10),
        enabled(11),
        platformDefault(4294967294)
    }

CucsBiosVfFrontPanelLockoutVpFrontPanelLockout ::= TEXTUAL-CONVENTION
    STATUS        current
    DESCRIPTION
        ""
    SYNTAX        INTEGER {
        platformRecommended(0),
        disabled(60),
        enabled(61),
        platformDefault(4294967294)
    }

CucsBiosVfIntelEntrySASRAIDModuleVpSASRAID ::= TEXTUAL-CONVENTION
    STATUS        current
    DESCRIPTION
        ""
    SYNTAX        INTEGER {
        platformRecommended(0),
        disabled(154),
        enabled(155),
        platformDefault(4294967294)
    }

CucsBiosVfIntelEntrySASRAIDModuleVpSASRAIDModule ::= TEXTUAL-CONVENTION
    STATUS        current
    DESCRIPTION
        ""
    SYNTAX        INTEGER {
        platformRecommended(0),
        itIrRaid(156),
        intelEsrtii(157),
        platformDefault(4294967294)
    }

CucsBiosVfIntelHyperThreadingTechVpIntelHyperThreadingTech ::= TEXTUAL-CONVENTION
    STATUS        current
    DESCRIPTION
        ""
    SYNTAX        INTEGER {
        platformRecommended(0),
        disabled(5),
        enabled(6),
        platformDefault(4294967294)
    }

CucsBiosVfIntelTurboBoostTechVpIntelTurboBoostTech ::= TEXTUAL-CONVENTION
    STATUS        current
    DESCRIPTION
        ""
    SYNTAX        INTEGER {
        platformRecommended(0),
        disabled(1),
        enabled(2),
        platformDefault(4294967294)
    }

CucsBiosVfIntelVTForDirectedIOVpIntelVTDATSSupport ::= TEXTUAL-CONVENTION
    STATUS        current
    DESCRIPTION
        ""
    SYNTAX        INTEGER {
        platformRecommended(0),
        disabled(20),
        enabled(21),
        platformDefault(4294967294)
    }

CucsBiosVfIntelVTForDirectedIOVpIntelVTDCoherencySupport ::= TEXTUAL-CONVENTION
    STATUS        current
    DESCRIPTION
        ""
    SYNTAX        INTEGER {
        platformRecommended(0),
        disabled(18),
        enabled(19),
        platformDefault(4294967294)
    }

CucsBiosVfIntelVTForDirectedIOVpIntelVTDInterruptRemapping ::= TEXTUAL-CONVENTION
    STATUS        current
    DESCRIPTION
        ""
    SYNTAX        INTEGER {
        platformRecommended(0),
        disabled(16),
        enabled(17),
        platformDefault(4294967294)
    }

CucsBiosVfIntelVTForDirectedIOVpIntelVTDPassThroughDMASupport ::= TEXTUAL-CONVENTION
    STATUS        current
    DESCRIPTION
        ""
    SYNTAX        INTEGER {
        platformRecommended(0),
        disabled(22),
        enabled(23),
        platformDefault(4294967294)
    }

CucsBiosVfIntelVTForDirectedIOVpIntelVTForDirectedIO ::= TEXTUAL-CONVENTION
    STATUS        current
    DESCRIPTION
        ""
    SYNTAX        INTEGER {
        platformRecommended(0),
        disabled(14),
        enabled(15),
        platformDefault(4294967294)
    }

CucsBiosVpIntelVirtualizationTechnology ::= TEXTUAL-CONVENTION
    STATUS        current
    DESCRIPTION
        ""
    SYNTAX        INTEGER {
        platformRecommended(0),
        disabled(12),
        enabled(13),
        platformDefault(4294967294)
    }

CucsBiosVfLvDIMMSupportVpLvDDRMode ::= TEXTUAL-CONVENTION
    STATUS        current
    DESCRIPTION
        ""
    SYNTAX        INTEGER {
        platformRecommended(0),
        powerSavingMode(137),
        performanceMode(138),
        platformDefault(4294967294)
    }

CucsBiosVfMaximumMemoryBelow4GBVpMaximumMemoryBelow4GB ::= TEXTUAL-CONVENTION
    STATUS        current
    DESCRIPTION
        ""
    SYNTAX        INTEGER {
        platformRecommended(0),
        disabled(54),
        enabled(55),
        platformDefault(4294967294)
    }

CucsBiosVfMemoryMappedIOAbove4GBVpMemoryMappedIOAbove4GB ::= TEXTUAL-CONVENTION
    STATUS        current
    DESCRIPTION
        ""
    SYNTAX        INTEGER {
        platformRecommended(0),
        disabled(56),
        enabled(57),
        platformDefault(4294967294)
    }

CucsBiosVfMirroringModeVpMirroringMode ::= TEXTUAL-CONVENTION
    STATUS        current
    DESCRIPTION
        ""
    SYNTAX        INTEGER {
        platformRecommended(0),
        interSocket(127),
        intraSocket(128),
        platformDefault(4294967294)
    }

CucsBiosVfNUMAOptimizedVpNUMAOptimized ::= TEXTUAL-CONVENTION
    STATUS        current
    DESCRIPTION
        ""
    SYNTAX        INTEGER {
        platformRecommended(0),
        disabled(32),
        enabled(33),
        platformDefault(4294967294)
    }

CucsBiosVfOSBootWatchdogTimerVpOSBootWatchdogTimer ::= TEXTUAL-CONVENTION
    STATUS        current
    DESCRIPTION
        ""
    SYNTAX        INTEGER {
        platformRecommended(0),
        disabled(114),
        enabled(115),
        platformDefault(4294967294)
    }

CucsBiosVfOSBootWatchdogTimerPolicyVpOSBootWatchdogTimerPolicy ::= TEXTUAL-CONVENTION
    STATUS        current
    DESCRIPTION
        ""
    SYNTAX        INTEGER {
        platformRecommended(0),
        powerOff(116),
        reset(162),
        platformDefault(4294967294)
    }

CucsBiosVfOSBootWatchdogTimerTimeOutVpOSBootWatchdogTimerPolicy ::= TEXTUAL-CONVENTION
    STATUS        current
    DESCRIPTION
        ""
    SYNTAX        INTEGER {
        platformRecommended(0),
        n5Minutes(171),
        n10Minutes(172),
        n15Minutes(173),
        n20Minutes(174),
        platformDefault(4294967294)
    }

CucsBiosVfOnboardSATAControllerVpOnboardSATAController ::= TEXTUAL-CONVENTION
    STATUS        current
    DESCRIPTION
        ""
    SYNTAX        INTEGER {
        platformRecommended(0),
        disabled(38),
        enabled(39),
        platformDefault(4294967294)
    }

CucsBiosVfOnboardSATAControllerVpSATAMode ::= TEXTUAL-CONVENTION
    STATUS        current
    DESCRIPTION
        ""
    SYNTAX        INTEGER {
        platformRecommended(0),
        enhanced(40),
        compatibility(41),
        ahci(42),
        swRaid(43),
        platformDefault(4294967294)
    }

CucsBiosVfOptionROMLoadVpLoad ::= TEXTUAL-CONVENTION
    STATUS        current
    DESCRIPTION
        ""
    SYNTAX        INTEGER {
        platformRecommended(0),
        platformDefault(4294967294)
    }

CucsBiosVfPOSTErrorPauseVpPOSTErrorPause ::= TEXTUAL-CONVENTION
    STATUS        current
    DESCRIPTION
        ""
    SYNTAX        INTEGER {
        platformRecommended(0),
        disabled(102),
        enabled(103),
        platformDefault(4294967294)
    }

CucsBiosVfProcessorC3ReportVpProcessorC3Report ::= TEXTUAL-CONVENTION
    STATUS        current
    DESCRIPTION
        ""
    SYNTAX        INTEGER {
        platformRecommended(0),
        disabled(108),
        acpiC2(135),
        acpiC3(136),
        platformDefault(4294967294)
    }

CucsBiosVfProcessorC6ReportVpProcessorC6Report ::= TEXTUAL-CONVENTION
    STATUS        current
    DESCRIPTION
        ""
    SYNTAX        INTEGER {
        platformRecommended(0),
        disabled(110),
        enabled(111),
        platformDefault(4294967294)
    }

CucsBiosVfQuietBootVpQuietBoot ::= TEXTUAL-CONVENTION
    STATUS        current
    DESCRIPTION
        ""
    SYNTAX        INTEGER {
        platformRecommended(0),
        disabled(100),
        enabled(101),
        platformDefault(4294967294)
    }

CucsBiosVfResumeOnACPowerLossVpResumeOnACPowerLoss ::= TEXTUAL-CONVENTION
    STATUS        current
    DESCRIPTION
        ""
    SYNTAX        INTEGER {
        platformRecommended(0),
        stayOff(70),
        lastState(71),
        reset(72),
        platformDefault(4294967294)
    }

CucsBiosVpSelectMemoryRASConfiguration ::= TEXTUAL-CONVENTION
    STATUS        current
    DESCRIPTION
        ""
    SYNTAX        INTEGER {
        platformRecommended(0),
        maximumPerformance(30),
        mirroring(31),
        sparing(125),
        lockstep(126),
        platformDefault(4294967294)
    }

CucsBiosVfSerialPortAEnableVpSerialPortAEnable ::= TEXTUAL-CONVENTION
    STATUS        current
    DESCRIPTION
        ""
    SYNTAX        INTEGER {
        platformRecommended(0),
        disabled(44),
        enabled(45),
        platformDefault(4294967294)
    }

CucsBiosVfSparingModeVpSparingMode ::= TEXTUAL-CONVENTION
    STATUS        current
    DESCRIPTION
        ""
    SYNTAX        INTEGER {
        platformRecommended(0),
        dimmSparing(126),
        rankSparing(127),
        platformDefault(4294967294)
    }

CucsBiosVfUEFIOSUseLegacyVideoVpUEFIOSUseLegacyVideo ::= TEXTUAL-CONVENTION
    STATUS        current
    DESCRIPTION
        ""
    SYNTAX        INTEGER {
        platformRecommended(0),
        disabled(160),
        enabled(161),
        platformDefault(4294967294)
    }

CucsBiosVfUSBBootConfigVpMakeDeviceNonBootable ::= TEXTUAL-CONVENTION
    STATUS        current
    DESCRIPTION
        ""
    SYNTAX        INTEGER {
        platformRecommended(0),
        disabled(106),
        enabled(107),
        platformDefault(4294967294)
    }

CucsBmcSELCntEqptClassId ::= TEXTUAL-CONVENTION
    STATUS        current
    DESCRIPTION
        ""
    SYNTAX        INTEGER {
        unspecified(0),
        processorUnit(142),
        memoryUnit(247),
        computeBoard(605)
    }

CucsBmcSELCntEqptInstIdPropId ::= TEXTUAL-CONVENTION
    STATUS        current
    DESCRIPTION
        ""
    SYNTAX        INTEGER {
        unspecified(0),
        processorUnitId(360),
        memoryUnitId(698)
    }

CucsBmcSELCntStatsClassId ::= TEXTUAL-CONVENTION
    STATUS        current
    DESCRIPTION
        ""
    SYNTAX        INTEGER {
        unspecified(0),
        computePCIeFatalProtocolStats(882),
        computePCIeFatalReceiveStats(884),
        computePCIeFatalCompletionStats(886),
        computePCIeFatalStats(888),
        processorErrorStats(1077),
        memoryErrorStats(1079)
    }

CucsCallhomeAdminState ::= TEXTUAL-CONVENTION
    STATUS        current
    DESCRIPTION
        ""
    SYNTAX        INTEGER {
        off(0),
        on(1)
    }

CucsCallhomeAlertGroup ::= TEXTUAL-CONVENTION
    STATUS        current
    DESCRIPTION
        ""
    SYNTAX        INTEGER {
        diagnostic(0),
        environmental(1),
        unknown(100)
    }

CucsCallhomeAlertGroups ::= TEXTUAL-CONVENTION
    STATUS        current
    DESCRIPTION
        ""
    SYNTAX        BITS {
        system(0),
        environmental(1),
        linecard(2),
        supervisor(3),
        inventory(4),
        test(5),
        ciscoTac(6),
        syslogPort(7),
        license(8),
        lifeCycle(9),
        diagnostic(10)
    }

CucsCallhomeAlertLevel ::= TEXTUAL-CONVENTION
    STATUS        current
    DESCRIPTION
        ""
    SYNTAX        INTEGER {
        debug(0),
        normal(1),
        notify(2),
        warning(3),
        minor(4),
        major(5),
        critical(6),
        fatal(7),
        unknown(100)
    }

CucsCallhomeAlertMessageSubtype ::= TEXTUAL-CONVENTION
    STATUS        current
    DESCRIPTION
        ""
    SYNTAX        INTEGER {
        nosubtype(0),
        test(1),
        full(2),
        delta(3),
        minor(4),
        major(5),
        goldnormal(6),
        goldminor(7),
        goldmajor(8),
        unknown(100)
    }

CucsCallhomeAlertMessageType ::= TEXTUAL-CONVENTION
    STATUS        current
    DESCRIPTION
        ""
    SYNTAX        INTEGER {
        inventory(0),
        syslog(1),
        test(2),
        diag(3),
        env(4),
        conf(5),
        unknown(100)
    }

CucsCallhomeAlertThrottlingAdminState ::= TEXTUAL-CONVENTION
    STATUS        current
    DESCRIPTION
        ""
    SYNTAX        INTEGER {
        off(0),
        on(1)
    }

CucsCallhomeEpFsmTaskItem ::= TEXTUAL-CONVENTION
    STATUS        current
    DESCRIPTION
        ""
    SYNTAX        INTEGER {
        nop(0),
        configCallhome(274)
    }

CucsCallhomeFormat ::= TEXTUAL-CONVENTION
    STATUS        current
    DESCRIPTION
        ""
    SYNTAX        INTEGER {
        xml(1),
        fullTxt(2),
        shortTxt(4)
    }

CucsCallhomeLevel ::= TEXTUAL-CONVENTION
    STATUS        current
    DESCRIPTION
        ""
    SYNTAX        INTEGER {
        debug(0),
        normal(1),
        notification(2),
        warning(3),
        minor(4),
        major(5),
        critical(6),
        fatal(7),
        disaster(8)
    }

CucsCallhomePolicyAdminState ::= TEXTUAL-CONVENTION
    STATUS        current
    DESCRIPTION
        ""
    SYNTAX        INTEGER {
        enabled(1),
        disabled(2)
    }

CucsCallhomeUrgency ::= TEXTUAL-CONVENTION
    STATUS        current
    DESCRIPTION
        ""
    SYNTAX        INTEGER {
        emergency(0),
        alert(1),
        critical(2),
        error(3),
        warning(4),
        notice(5),
        info(6),
        debug(7)
    }

CucsCapabilityAdminState ::= TEXTUAL-CONVENTION
    STATUS        current
    DESCRIPTION
        ""
    SYNTAX        INTEGER {
        restart(0),
        idle(1)
    }

CucsCapabilityCatalogueFsmTaskItem ::= TEXTUAL-CONVENTION
    STATUS        current
    DESCRIPTION
        ""
    SYNTAX        INTEGER {
        nop(0),
        deployCatalogue(839),
        activateCatalog(893)
    }

CucsCapabilityMgmtExtensionFsmTaskItem ::= TEXTUAL-CONVENTION
    STATUS        current
    DESCRIPTION
        ""
    SYNTAX        INTEGER {
        nop(0),
        activateMgmtExt(899)
    }

CucsCapabilityOperStatus ::= TEXTUAL-CONVENTION
    STATUS        current
    DESCRIPTION
        ""
    SYNTAX        INTEGER {
        init(0),
        downloading(1),
        downloaded(2),
        applied(3),
        failed(4)
    }

CucsCapabilityUpdaterFsmTaskItem ::= TEXTUAL-CONVENTION
    STATUS        current
    DESCRIPTION
        ""
    SYNTAX        INTEGER {
        nop(0),
        updater(582)
    }

CucsCommAdminState ::= TEXTUAL-CONVENTION
    STATUS        current
    DESCRIPTION
        ""
    SYNTAX        INTEGER {
        enabled(1),
        disabled(2)
    }

CucsCommChannel ::= TEXTUAL-CONVENTION
    STATUS        current
    DESCRIPTION
        ""
    SYNTAX        INTEGER {
        fullssl(0),
        noencssl(1),
        plain(2)
    }

CucsCommClientAdminState ::= TEXTUAL-CONVENTION
    STATUS        current
    DESCRIPTION
        ""
    SYNTAX        INTEGER {
        enabled(1),
        disabled(2)
    }

CucsCommDnsProviderAdminState ::= TEXTUAL-CONVENTION
    STATUS        current
    DESCRIPTION
        ""
    SYNTAX        INTEGER {
        enabled(1),
        disabled(2)
    }

CucsCommFilePathProtocol ::= TEXTUAL-CONVENTION
    STATUS        current
    DESCRIPTION
        ""
    SYNTAX        INTEGER {
        none(0),
        workspace(1),
        volatile(2),
        ftp(3),
        tftp(4),
        scp(5),
        sftp(6)
    }

CucsCommNtpProviderAdminState ::= TEXTUAL-CONVENTION
    STATUS        current
    DESCRIPTION
        ""
    SYNTAX        INTEGER {
        enabled(1),
        disabled(2)
    }

CucsCommProtocol ::= TEXTUAL-CONVENTION
    STATUS        current
    DESCRIPTION
        ""
    SYNTAX        INTEGER {
        none(0),
        tcp(1),
        udp(2),
        all(3)
    }

CucsCommShellProto ::= TEXTUAL-CONVENTION
    STATUS        current
    DESCRIPTION
        ""
    SYNTAX        INTEGER {
        none(0),
        tcp(1),
        udp(2),
        all(3)
    }

CucsCommSmashCLPProto ::= TEXTUAL-CONVENTION
    STATUS        current
    DESCRIPTION
        ""
    SYNTAX        INTEGER {
        none(0),
        tcp(1),
        udp(2),
        all(3)
    }

CucsCommSnmpProto ::= TEXTUAL-CONVENTION
    STATUS        current
    DESCRIPTION
        ""
    SYNTAX        INTEGER {
        none(0),
        tcp(1),
        udp(2),
        all(3)
    }

CucsCommSnmpAuth ::= TEXTUAL-CONVENTION
    STATUS        current
    DESCRIPTION
        ""
    SYNTAX        INTEGER {
        md5(1),
        sha(2)
    }

CucsCommSnmpNotificationType ::= TEXTUAL-CONVENTION
    STATUS        current
    DESCRIPTION
        ""
    SYNTAX        INTEGER {
        traps(1),
        informs(2)
    }

CucsCommSnmpV3Privilege ::= TEXTUAL-CONVENTION
    STATUS        current
    DESCRIPTION
        ""
    SYNTAX        INTEGER {
        auth(1),
        noauth(2),
        priv(3)
    }

CucsCommSnmpVersion ::= TEXTUAL-CONVENTION
    STATUS        current
    DESCRIPTION
        ""
    SYNTAX        INTEGER {
        v1(1),
        v2c(2),
        v3(3)
    }

CucsCommSvcEpFsmTaskFlags ::= TEXTUAL-CONVENTION
    STATUS        current
    DESCRIPTION
        ""
    SYNTAX        BITS {
        samDmeCommSvcEpUpdateSvcEpEpChange(21),
        samDmeCommSvcEpUpdateSvcEpPropogateSettings(22)
    }

CucsCommSvcEpFsmTaskItem ::= TEXTUAL-CONVENTION
    STATUS        current
    DESCRIPTION
        ""
    SYNTAX        INTEGER {
        nop(0),
        updateSvcEp(190),
        restartWebSvc(193)
    }

CucsCommSyslogProto ::= TEXTUAL-CONVENTION
    STATUS        current
    DESCRIPTION
        ""
    SYNTAX        INTEGER {
        none(0),
        tcp(1),
        udp(2),
        all(3)
    }

CucsCommSyslogAdminState ::= TEXTUAL-CONVENTION
    STATUS        current
    DESCRIPTION
        ""
    SYNTAX        INTEGER {
        enabled(1),
        disabled(2)
    }

CucsCommSyslogClientEnum ::= TEXTUAL-CONVENTION
    STATUS        current
    DESCRIPTION
        ""
    SYNTAX        INTEGER {
        primary(1),
        secondary(2),
        tertiary(3)
    }

CucsCommSyslogFileSize ::= TEXTUAL-CONVENTION
    STATUS        current
    DESCRIPTION
        ""
    SYNTAX        Gauge32 (4096..4194304)

CucsCommSyslogForwardingFacility ::= TEXTUAL-CONVENTION
    STATUS        current
    DESCRIPTION
        ""
    SYNTAX        INTEGER {
        local0(0),
        local1(1),
        local2(2),
        local3(3),
        local4(4),
        local5(5),
        local6(6),
        local7(7)
    }

CucsCommSyslogRestrictedSeverity ::= TEXTUAL-CONVENTION
    STATUS        current
    DESCRIPTION
        ""
    SYNTAX        INTEGER {
        emergencies(0),
        alerts(1),
        critical(2)
    }

CucsCommSyslogSeverity ::= TEXTUAL-CONVENTION
    STATUS        current
    DESCRIPTION
        ""
    SYNTAX        INTEGER {
        emergencies(0),
        alerts(1),
        critical(2),
        errors(3),
        warnings(4),
        notifications(5),
        information(6),
        debugging(7)
    }

CucsCommWebProto ::= TEXTUAL-CONVENTION
    STATUS        current
    DESCRIPTION
        ""
    SYNTAX        INTEGER {
        none(0),
        tcp(1),
        udp(2),
        all(3)
    }

CucsCommXmlClConnPolicyClientType ::= TEXTUAL-CONVENTION
    STATUS        current
    DESCRIPTION
        ""
    SYNTAX        INTEGER {
        javaUi(0),
        flexUi(1),
        extrenalApiClient(2)
    }

CucsComputeAdminPowerState ::= TEXTUAL-CONVENTION
    STATUS        current
    DESCRIPTION
        ""
    SYNTAX        INTEGER {
        cycleImmediate(2),
        cycleWait(3),
        hardResetImmediate(4),
        hardResetWait(5),
        cmosResetImmediate(12),
        bmcResetImmediate(13),
        bmcResetWait(14),
        diagnosticInterrupt(15),
        kvmReset(16),
        policy(30)
    }

CucsComputeAdminState ::= TEXTUAL-CONVENTION
    STATUS        current
    DESCRIPTION
        ""
    SYNTAX        INTEGER {
        inService(1),
        outOfService(2)
    }

CucsComputeAdminTrigger ::= TEXTUAL-CONVENTION
    STATUS        current
    DESCRIPTION
        ""
    SYNTAX        INTEGER {
        undiscovered(0),
        rediscover(1),
        resetToFactory(2),
        discovered(3),
        remove(4),
        migrate(5),
        decommission(6)
    }

CucsComputeAssociation ::= TEXTUAL-CONVENTION
    STATUS        current
    DESCRIPTION
        ""
    SYNTAX        INTEGER {
        none(0),
        establishing(1),
        associated(2),
        removing(3),
        failed(4),
        throttled(5)
    }

CucsComputeAvailability ::= TEXTUAL-CONVENTION
    STATUS        current
    DESCRIPTION
        ""
    SYNTAX        INTEGER {
        unavailable(0),
        available(1)
    }

CucsComputeBladeSlotId ::= TEXTUAL-CONVENTION
    STATUS        current
    DESCRIPTION
        ""
    SYNTAX        Gauge32 (1..8)

CucsComputeBladeFsmTaskFlags ::= TEXTUAL-CONVENTION
    STATUS        current
    DESCRIPTION
        ""
    SYNTAX        BITS {
        samDmeComputeBladeDiscoverCheckPoint(0),
        samDmeComputeBladeDiagEfiDiag(18),
        samDmeComputeBladeDiagDetailDiag(20),
        samDmeComputeBladeDiagCancelDiag(23)
    }

CucsComputeBladeFsmTaskItem ::= TEXTUAL-CONVENTION
    STATUS        current
    DESCRIPTION
        ""
    SYNTAX        INTEGER {
        nop(0),
        discover(23),
        diag(144),
        updateBoardController(834)
    }

CucsComputeChassisDiscAction ::= TEXTUAL-CONVENTION
    STATUS        current
    DESCRIPTION
        ""
    SYNTAX        INTEGER {
        immediate(0),
        userAcknowledged(1),
        n1Link(2),
        n2Link(3),
        n4Link(4)
    }

CucsComputeChassisQualMaxId ::= TEXTUAL-CONVENTION
    STATUS        current
    DESCRIPTION
        ""
    SYNTAX        Gauge32 (1..255)

CucsComputeChassisQualMinId ::= TEXTUAL-CONVENTION
    STATUS        current
    DESCRIPTION
        ""
    SYNTAX        Gauge32 (1..255)

CucsComputeCheckPoint ::= TEXTUAL-CONVENTION
    STATUS        current
    DESCRIPTION
        ""
    SYNTAX        INTEGER {
        unknown(0),
        removing(1),
        shallowCheckpoint(2),
        deepCheckpoint(3),
        discovered(4)
    }

CucsComputeConnectivityRebalancing ::= TEXTUAL-CONVENTION
    STATUS        current
    DESCRIPTION
        ""
    SYNTAX        INTEGER {
        immediate(0),
        userAcknowledged(1)
    }

CucsComputeDiscovery ::= TEXTUAL-CONVENTION
    STATUS        current
    DESCRIPTION
        ""
    SYNTAX        INTEGER {
        undiscovered(0),
        inProgress(1),
        malformedFruInfo(2),
        fruNotReady(3),
        insufficientlyEquipped(4),
        failed(8),
        complete(16),
        retry(32),
        throttled(64),
        illegalFru(128),
        fruIdentityIndeterminate(129),
        fruStateIndeterminate(130),
        diagnosticsInProgress(131),
        efidiagnosticsInProgress(132),
        diagnosticsFailed(133),
        diagnosticsComplete(134),
        waitingForUserAck(135),
        userAcknowledged(136)
    }

CucsComputeIOHubEnvStatsThresholded ::= TEXTUAL-CONVENTION
    STATUS        current
    DESCRIPTION
        ""
    SYNTAX        BITS {
        temperature(0),
        temperatureAvg(1),
        temperatureMax(2),
        temperatureMin(3)
    }

CucsComputeIOHubEnvStatsHistThresholded ::= TEXTUAL-CONVENTION
    STATUS        current
    DESCRIPTION
        ""
    SYNTAX        BITS {
        temperature(0),
        temperatureAvg(1),
        temperatureMax(2),
        temperatureMin(3)
    }

CucsComputeIssues ::= TEXTUAL-CONVENTION
    STATUS        current
    DESCRIPTION
        ""
    SYNTAX        BITS {
        computeThermal(0),
        computeInoperable(1),
        computeVoltage(2),
        computePerf(3),
        computePower(4),
        removed(5),
        config(6),
        computePostFailure(7),
        cpuThermal(8),
        cpuInoperable(9),
        cpuVoltage(10),
        cpuPerf(11),
        cpuPower(12),
        memoryThermal(13),
        memoryInoperable(14),
        memoryVoltage(15),
        memoryPerf(16),
        memoryPower(17),
        adaptorThermal(18),
        adaptorInoperable(19),
        adaptorVoltage(20),
        adaptorPerf(21),
        adaptorPower(22),
        nicThermal(23),
        nicInoperable(24),
        nicVoltage(25),
        nicPerf(26),
        nicPower(27),
        hbaThermal(28),
        hbaInoperable(29),
        hbaVoltage(30),
        hbaPerf(31),
        hbaPower(32),
        mismatch(33)
    }

CucsComputeMbPowerStatsThresholded ::= TEXTUAL-CONVENTION
    STATUS        current
    DESCRIPTION
        ""
    SYNTAX        BITS {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CucsComputeMbPowerStatsHistThresholded ::= TEXTUAL-CONVENTION
    STATUS        current
    DESCRIPTION
        ""
    SYNTAX        BITS {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CucsComputeMbTempStatsThresholded ::= TEXTUAL-CONVENTION
    STATUS        current
    DESCRIPTION
        ""
    SYNTAX        BITS {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CucsComputeMbTempStatsHistThresholded ::= TEXTUAL-CONVENTION
    STATUS        current
    DESCRIPTION
        ""
    SYNTAX        BITS {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CucsComputeMemoryUnitConstraintType ::= TEXTUAL-CONVENTION
    STATUS        current
    DESCRIPTION
        ""
    SYNTAX        INTEGER {
        unknown(0),
        kit(1)
    }

CucsComputeOwner ::= TEXTUAL-CONVENTION
    STATUS        current
    DESCRIPTION
        ""
    SYNTAX        INTEGER {
        policy(1),
        management(2)
    }

CucsComputePCIeFatalCompletionStatsThresholded ::= TEXTUAL-CONVENTION
    STATUS        current
    DESCRIPTION
        ""
    SYNTAX        BITS {
        abortErrors(0),
        timeoutErrors(1),
        unexpectedErrors(2)
    }

CucsComputePCIeFatalProtocolStatsThresholded ::= TEXTUAL-CONVENTION
    STATUS        current
    DESCRIPTION
        ""
    SYNTAX        BITS {
        dllpErrors(0),
        flowControlErrors(1)
    }

CucsComputePCIeFatalReceiveStatsThresholded ::= TEXTUAL-CONVENTION
    STATUS        current
    DESCRIPTION
        ""
    SYNTAX        BITS {
        bufferOverflowErrors(0),
        errFatalErrors(1),
        errNonFatalErrors(2),
        unsupportedRequestErrors(3)
    }

CucsComputePCIeFatalStatsThresholded ::= TEXTUAL-CONVENTION
    STATUS        current
    DESCRIPTION
        ""
    SYNTAX        BITS {
        acsViolationErrors(0),
        malformedTLPErrors(1),
        poisonedTLPErrors(2),
        surpriseLinkDownErrors(3)
    }

CucsComputePciCapOrder ::= TEXTUAL-CONVENTION
    STATUS        current
    DESCRIPTION
        ""
    SYNTAX        INTEGER {
        ascending(0),
        descending(1)
    }

CucsComputePhysicalLowVoltageMemory ::= TEXTUAL-CONVENTION
    STATUS        current
    DESCRIPTION
        ""
    SYNTAX        INTEGER

CucsComputePhysicalFsmTaskFlags ::= TEXTUAL-CONVENTION
    STATUS        current
    DESCRIPTION
        ""
    SYNTAX        BITS {
        samDmeComputePhysicalAssociatePnuosConfig(26),
        samDmeComputePhysicalAssociateSwitchConfig(27),
        samDmeComputePhysicalAssociateHostConfig(28),
        samDmeComputePhysicalAssociateHostReboot(29),
        samDmeComputePhysicalAssociateIfConfig(30),
        samDmeComputePhysicalAssociateNicConfig(31),
        samDmeComputePhysicalAssociateAdaptorNwFwConfig(32),
        samDmeComputePhysicalAssociateMgmtFwConfig(33),
        samDmeComputePhysicalAssociateBootConfig(34),
        samDmeComputePhysicalAssociateBiosUpdate(35),
        samDmeComputePhysicalAssociateSolConfig(36),
        samDmeComputePhysicalAssociateEpAuthConfig(37),
        samDmeComputePhysicalAssociateDiskConfig(38),
        samDmeComputePhysicalDisassociateSwitchUnconfig(39),
        samDmeComputePhysicalActivateAdaptorActivate(40),
        samDmeComputePhysicalActivateAdaptorReset(41),
        samDmeComputePhysicalCmosResetAlways(42),
        samDmeComputePhysicalCmosResetSetUuidBiosBoot(43),
        samDmeComputePhysicalCmosResetPowerOn(44),
        samDmeComputePhysicalAssociateBoardCtrlFwConfig(45)
    }

CucsComputePhysicalFsmTaskItem ::= TEXTUAL-CONVENTION
    STATUS        current
    DESCRIPTION
        ""
    SYNTAX        INTEGER {
        nop(0),
        associate(634),
        disassociate(680),
        decommission(711),
        softShutdown(713),
        hardShutdown(715),
        turnup(717),
        powercycle(719),
        hardreset(723),
        softreset(727),
        swConnUpd(731),
        biosRecovery(734),
        cmosReset(748),
        resetBmc(752),
        updateExtUsers(754),
        updateAdaptor(756),
        activateAdaptor(761),
        configSoL(765),
        unconfigSoL(767),
        diagnosticInterrupt(1036),
        resetKvm(1055)
    }

CucsComputePooledRackUnitId ::= TEXTUAL-CONVENTION
    STATUS        current
    DESCRIPTION
        ""
    SYNTAX        Gauge32 (1..255)

CucsComputePooledSlotSlotId ::= TEXTUAL-CONVENTION
    STATUS        current
    DESCRIPTION
        ""
    SYNTAX        Gauge32 (1..8)

CucsComputePsuClusterState ::= TEXTUAL-CONVENTION
    STATUS        current
    DESCRIPTION
        ""
    SYNTAX        INTEGER {
        unknown(0),
        slot1Master(1),
        slot2Master(2),
        notClustered(3)
    }

CucsComputePsuControlRedundancy ::= TEXTUAL-CONVENTION
    STATUS        current
    DESCRIPTION
        ""
    SYNTAX        INTEGER {
        unknown(0),
        nonRedundant(1),
        nPlus1(2),
        grid(3)
    }

CucsComputePsuRedundancy ::= TEXTUAL-CONVENTION
    STATUS        current
    DESCRIPTION
        ""
    SYNTAX        INTEGER {
        nonRedundant(1),
        nPlus1(2),
        grid(3)
    }

CucsComputePsuRedundancyOperQualifier ::= TEXTUAL-CONVENTION
    STATUS        current
    DESCRIPTION
        ""
    SYNTAX        BITS {
        redundancyLost(0),
        redundancyDegraded(1),
        nonRedundantSufficientResources(2),
        nonRedundantInsufficientResources(3)
    }

CucsComputePsuRedundancyOperState ::= TEXTUAL-CONVENTION
    STATUS        current
    DESCRIPTION
        ""
    SYNTAX        INTEGER {
        unknown(0),
        ok(1),
        failed(2),
        degraded(3)
    }

CucsComputeRackQualMaxId ::= TEXTUAL-CONVENTION
    STATUS        current
    DESCRIPTION
        ""
    SYNTAX        Gauge32 (1..255)

CucsComputeRackQualMinId ::= TEXTUAL-CONVENTION
    STATUS        current
    DESCRIPTION
        ""
    SYNTAX        Gauge32 (1..255)

CucsComputeRackUnitId ::= TEXTUAL-CONVENTION
    STATUS        current
    DESCRIPTION
        ""
    SYNTAX        Gauge32 (1..255)

CucsComputeRackUnitFsmTaskFlags ::= TEXTUAL-CONVENTION
    STATUS        current
    DESCRIPTION
        ""
    SYNTAX        BITS {
        samDmeComputeRackUnitDiscoverCheckPoint(24)
    }

CucsComputeRackUnitFsmTaskItem ::= TEXTUAL-CONVENTION
    STATUS        current
    DESCRIPTION
        ""
    SYNTAX        INTEGER {
        nop(0),
        discover(599),
        offline(1064)
    }

CucsComputeRackUnitMbTempStatsThresholded ::= TEXTUAL-CONVENTION
    STATUS        current
    DESCRIPTION
        ""
    SYNTAX        BITS {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CucsComputeRackUnitMbTempStatsHistThresholded ::= TEXTUAL-CONVENTION
    STATUS        current
    DESCRIPTION
        ""
    SYNTAX        BITS {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CucsComputeScrubAction ::= TEXTUAL-CONVENTION
    STATUS        current
    DESCRIPTION
        ""
    SYNTAX        INTEGER {
        no(0),
        yes(1)
    }

CucsComputeSlotQualMaxId ::= TEXTUAL-CONVENTION
    STATUS        current
    DESCRIPTION
        ""
    SYNTAX        Gauge32 (1..8)

CucsComputeSlotQualMinId ::= TEXTUAL-CONVENTION
    STATUS        current
    DESCRIPTION
        ""
    SYNTAX        Gauge32 (1..8)

CucsConditionCallHomeCause ::= TEXTUAL-CONVENTION
    STATUS        current
    DESCRIPTION
        ""
    SYNTAX        INTEGER {
        unspecified(0),
        equipmentInoperable(1),
        thermalProblem(2),
        connectivityProblem(3),
        licenseGraceperiodExpired(4),
        mgmtifDown(5),
        linkDown(6),
        electionFailure(7),
        managementServicesFailure(8),
        managementServicesUnresponsive(9),
        versionIncompatible(10),
        identityUnestablishable(11),
        equipmentInaccessible(12),
        configurationFailure(13),
        associationFailed(14),
        powerProblem(15),
        equipmentProblem(16),
        voltageProblem(17),
        fruProblem(18)
    }

CucsConditionCause ::= TEXTUAL-CONVENTION
    STATUS        current
    DESCRIPTION
        ""
    SYNTAX        INTEGER {
        unknown(0),
        transition(1),
        beginFailed(2),
        fsmFailed(3),
        checkLicenseFailed(4),
        identifyFailed(5),
        configureSwMgmtEndPointFailed(6),
        configureVifNsFailed(7),
        configureEndPointFailed(8),
        discoverChassisFailed(9),
        enableChassisFailed(10),
        decomissionFailed(11),
        unIdentifyLocalFailed(12),
        cleanupEntriesFailed(13),
        waitFailed(14),
        disableEndPointFailed(15),
        unIdentifyPeerFailed(16),
        executeFailed(17),
        deployFailed(18),
        bmcConfigureConnLocalFailed(20),
        swConfigureConnLocalFailed(21),
        bmcConfigureConnPeerFailed(22),
        swConfigureConnPeerFailed(23),
        bmcPresenceFailed(24),
        bmcInventoryFailed(25),
        preSanitizeFailed(26),
        sanitizeFailed(27),
        configUserAccessFailed(28),
        swConfigPnuoslocalFailed(29),
        swConfigPnuospeerFailed(30),
        configDiscoveryModeFailed(31),
        swUnconfigPortNivLocalFailed(32),
        swUnconfigPortNivPeerFailed(33),
        bootPnuosFailed(35),
        bootWaitFailed(36),
        biosPostCompletionFailed(37),
        readSmbiosFailed(38),
        hagConnectFailed(39),
        pnuosidentFailed(40),
        pnuospolicyFailed(41),
        pnuosinventoryFailed(42),
        pnuosscrubFailed(43),
        pnuosconnectivityFailed(44),
        pnuosconnStatusFailed(45),
        swPnuosconnectivityLocalFailed(46),
        swPnuosconnectivityPeerFailed(47),
        pnuosselfTestFailed(48),
        hagDisconnectFailed(51),
        bmcShutdownDiscoveredFailed(52),
        handlePoolingFailed(53),
        successFailed(54),
        failFailed(55),
        configFeLocalFailed(56),
        swConfigPortNivLocalFailed(57),
        swConfigPortNivPeerFailed(58),
        nicPresenceLocalFailed(59),
        nicPresencePeerFailed(60),
        nicInventoryLocalFailed(61),
        nicInventoryPeerFailed(62),
        deriveConfigFailed(63),
        configSolFailed(64),
        swConfigLocalFailed(65),
        swConfigPeerFailed(66),
        nicConfigLocalFailed(67),
        nicConfigPeerFailed(68),
        stopvmediaLocalFailed(69),
        stopvmediaPeerFailed(70),
        setupvmediaLocalFailed(71),
        setupvmediaPeerFailed(72),
        bladeBootFailed(73),
        bladeBootWaitFailed(74),
        bladeReadSmbiosFailed(75),
        hostConnectFailed(76),
        startMemoryTestStatusFailed(77),
        pollMemoryTestStatusFailed(78),
        hostIdentFailed(79),
        hostPolicyFailed(80),
        setDiagUserFailed(81),
        hostInventoryFailed(82),
        hostServerDiagFailed(83),
        hostServerDiagStatusFailed(84),
        disableServerConnSwBfailed(85),
        startFabricatrafficTestFailed(86),
        fabricatrafficTestStatusFailed(87),
        enableServerConnSwBfailed(88),
        disableServerConnSwAfailed(89),
        startFabricbtrafficTestFailed(90),
        fabricbtrafficTestStatusFailed(91),
        enableServerConnSwAfailed(92),
        generateReportFailed(93),
        generateLogWaitFailed(94),
        debugWaitFailed(95),
        removevmediaLocalFailed(96),
        removevmediaPeerFailed(97),
        nicUnconfigLocalFailed(98),
        nicUnconfigPeerFailed(99),
        swUnconfigLocalFailed(100),
        swUnconfigPeerFailed(101),
        removeConfigFailed(102),
        restoreConfigFeLocalFailed(103),
        restoreConfigFePeerFailed(104),
        unconfigUserAccessFailed(105),
        unconfigSolFailed(106),
        hostDisconnectFailed(107),
        bmcShutdownDiagCompletedFailed(108),
        evaluateStatusFailed(109),
        primaryFailed(110),
        secondaryFailed(111),
        executeLocalFailed(112),
        executePeerFailed(113),
        nicConfigPnuoslocalFailed(114),
        nicConfigPnuospeerFailed(115),
        setupVmediaLocalFailed(116),
        setupVmediaPeerFailed(117),
        bladeBootPnuosFailed(118),
        nicUnconfigPnuoslocalFailed(119),
        nicUnconfigPnuospeerFailed(120),
        swUnconfigPnuoslocalFailed(121),
        swUnconfigPnuospeerFailed(122),
        teardownVmediaLocalFailed(123),
        teardownVmediaPeerFailed(124),
        updateibmcfwFailed(125),
        waitForibmcfwUpdateFailed(126),
        activateibmcfwFailed(127),
        resetibmcFailed(128),
        powerOnFailed(129),
        updateAdaptorNwFwLocalFailed(130),
        updateAdaptorNwFwPeerFailed(131),
        waitForAdaptorNwFwUpdateLocalFailed(132),
        waitForAdaptorNwFwUpdatePeerFailed(133),
        activateAdaptorNwFwLocalFailed(134),
        activateAdaptorNwFwPeerFailed(135),
        hagPnuosconnectFailed(136),
        pnuosvalidateFailed(137),
        biosImgUpdateFailed(138),
        storageCtlrImgUpdateFailed(139),
        hbaImgUpdateFailed(140),
        nicImgUpdateFailed(141),
        pnuosconfigFailed(142),
        pnuoslocalDiskConfigFailed(143),
        swConfigHostoslocalFailed(144),
        swConfigHostospeerFailed(145),
        nicConfigHostoslocalFailed(146),
        nicConfigHostospeerFailed(147),
        hagPnuosdisconnectFailed(148),
        pnuosunloadDriversFailed(149),
        prepareForBootFailed(150),
        configUuidFailed(151),
        bootHostFailed(152),
        waitForConnReadyFailed(153),
        hostosidentFailed(154),
        hostospolicyFailed(155),
        hostosvalidateFailed(156),
        hostosconfigFailed(157),
        nicUnconfigHostoslocalFailed(158),
        nicUnconfigHostospeerFailed(159),
        swUnconfigHostoslocalFailed(160),
        swUnconfigHostospeerFailed(161),
        pnuosunconfigFailed(162),
        unconfigUuidFailed(163),
        shutdownFailed(164),
        unconfigSoLfailed(165),
        configFailed(166),
        swUnconfigureLocalFailed(167),
        swUnconfigurePeerFailed(168),
        startFailed(169),
        cleanupFailed(170),
        resetFailed(171),
        unconfigBiosFailed(172),
        applyTemplateFailed(173),
        applyIdentifiersFailed(174),
        applyPoliciesFailed(175),
        resolveBootConfigFailed(176),
        evaluateAssociationFailed(177),
        analyzeImpactFailed(178),
        waitForMaintPermissionFailed(179),
        waitForMaintWindowFailed(180),
        reconfigUuidFailed(181),
        updateEthMonFailed(182),
        updateFcMonFailed(183),
        serverMoved(186),
        serverIdentificationProblem(187),
        primaryVlanMissingIsolated(188),
        namedPolicyUnresolved(189),
        localFailed(190),
        peerFailed(191),
        configurationFailed(192),
        equipmentInoperable(193),
        thermalProblem(194),
        voltageProblem(195),
        capacityExceeded(196),
        equipmentDegraded(197),
        identityUnestablishable(198),
        setEpLocalFailed(199),
        setEpPeerFailed(200),
        propogateEpSettingsFailed(201),
        propogateEpTimeZoneSettingsLocalFailed(202),
        propogateEpTimeZoneSettingsPeerFailed(203),
        restartFailed(204),
        setRealmLocalFailed(205),
        setRealmPeerFailed(206),
        setUserPeerFailed(208),
        setKeyRingLocalFailed(209),
        setKeyRingPeerFailed(210),
        unidentifiableFru(211),
        equipmentMissing(212),
        connectivityProblem(213),
        linkDown(214),
        linkMisconnected(215),
        disableFailed(216),
        enableFailed(217),
        disableAfailed(218),
        enableAfailed(219),
        propogateEpTimeZoneSettingsToAdaptorsLocalFailed(220),
        propogateEpTimeZoneSettingsToAdaptorsPeerFailed(221),
        vifDown(222),
        updateConnectivityFailed(223),
        createLocalFailed(224),
        createRemoteFailed(225),
        unpackLocalFailed(226),
        deleteLocalFailed(227),
        copyRemoteFailed(228),
        remoteFailed(229),
        updateLocalFailed(230),
        verifyLocalFailed(231),
        resetLocalFailed(232),
        updateRemoteFailed(233),
        verifyRemoteFailed(234),
        resetRemoteFailed(235),
        updateRequestFailed(236),
        pollUpdateStatusFailed(237),
        activateFailed(238),
        updateRequestLocalFailed(239),
        updateRequestPeerFailed(240),
        pollUpdateStatusLocalFailed(241),
        pollUpdateStatusPeerFailed(242),
        powerOffFailed(243),
        copyPrimaryFailed(244),
        imageDeleted(245),
        imageUnusable(246),
        imageCannotBoot(247),
        psuInsufficient(248),
        rescanImagesFailed(249),
        applyCatalogFailed(250),
        syncBladeaglocalFailed(251),
        syncBladeagremoteFailed(252),
        syncNicaglocalFailed(253),
        syncNicagremoteFailed(254),
        syncPortaglocalFailed(255),
        syncPortagremoteFailed(256),
        syncHostagentaglocalFailed(257),
        syncHostagentagremoteFailed(258),
        finalizeFailed(259),
        validateLocalFailed(260),
        validateRemoteFailed(261),
        deleteRemoteFailed(262),
        licenseGraceperiodEntered(263),
        licenseGraceperiod10days(264),
        oldChassisComponentFirmware(265),
        licenseGraceperiod60days(266),
        psuFailure(267),
        psuRedundancyFail(268),
        licenseGraceperiodExpired(269),
        powerConsumptionHitLimit(270),
        noAckFromBios(271),
        portFailed(272),
        interfaceFailed(273),
        operationalStateDown(274),
        cmcVifDown(275),
        setLocalFailed(276),
        setPeerFailed(277),
        switchFailed(278),
        limitReached(279),
        emptyPool(280),
        decommissioned(283),
        uploadFailed(284),
        downloadLocalFailed(285),
        tftpServerError(286),
        electionFailure(287),
        managementServicesFailure(288),
        managementServicesUnresponsive(289),
        haNotReady(290),
        versionIncompatible(291),
        logCapacity(293),
        fileTransferFailed(294),
        insufficientResources(296),
        insufficientlyEquipped(297),
        powerProblem(298),
        discoveryFailed(299),
        associationFailed(300),
        unsupportedTransceiver(301),
        equipmentProblem(302),
        discoveryInProgress(303),
        configurationInProgress(304),
        unconfigurationInProgress(305),
        poweredOff(306),
        inMaintenance(307),
        underTest(308),
        serverUnassociated(309),
        serverAssociating(310),
        unassociated(311),
        serverDeassociating(312),
        serverUnassigned(313),
        serverAssigned(314),
        configurationNotApplied(315),
        configurationApplying(316),
        propogateEpTimeZoneSettingsToFexIomLocalFailed(317),
        serverFailed(318),
        configurationFailure(319),
        maintenanceFailed(320),
        equipmentRemoved(321),
        serverInaccessible(322),
        getVersionFailed(324),
        removeLocalFailed(325),
        setEpAfailed(326),
        setEpBfailed(327),
        satelliteConnectionAbsent(328),
        satelliteConnectionInit(329),
        satelliteMisConnected(330),
        unexpectedNumberOfLinks(331),
        equipmentOffline(332),
        performanceProblem(333),
        firmwareUpgradeProblem(334),
        unsupportedConnectivityConfiguration(335),
        equipmentUnacknowledged(336),
        autoFirmwareUpgrade(337),
        equipmentDisconnected(338),
        fruProblem(339),
        thresholdCrossed(340),
        deviceSEEPROMIOError(345),
        assignmentFailed(353),
        deviceSeepromError(355),
        newLink(360)
    }

CucsConditionCode ::= TEXTUAL-CONVENTION
    STATUS        current
    DESCRIPTION
        ""
    SYNTAX        INTEGER {
        generic(0),
        f0156(156),
        f0157(157),
        f0169(169),
        f0170(170),
        f0174(174),
        f0175(175),
        f0176(176),
        f0177(177),
        f0178(178),
        f0179(179),
        f0180(180),
        f0181(181),
        f0182(182),
        f0183(183),
        f0184(184),
        f0185(185),
        f0186(186),
        f0187(187),
        f0188(188),
        f0189(189),
        f0190(190),
        f0191(191),
        f0200(200),
        f0203(203),
        f0206(206),
        f0207(207),
        f0209(209),
        f0276(276),
        f0277(277),
        f0278(278),
        f0279(279),
        f0282(282),
        f0283(283),
        f0291(291),
        f0293(293),
        f0294(294),
        f0304(304),
        f0305(305),
        f0306(306),
        f0310(310),
        f0311(311),
        f0312(312),
        f0313(313),
        f0314(314),
        f0315(315),
        f0317(317),
        f0318(318),
        f0319(319),
        f0320(320),
        f0321(321),
        f0322(322),
        f0324(324),
        f0326(326),
        f0327(327),
        f0329(329),
        f0330(330),
        f0331(331),
        f0332(332),
        f0334(334),
        f0337(337),
        f0367(367),
        f0368(368),
        f0369(369),
        f0371(371),
        f0373(373),
        f0374(374),
        f0376(376),
        f0377(377),
        f0378(378),
        f0379(379),
        f0380(380),
        f0381(381),
        f0382(382),
        f0383(383),
        f0384(384),
        f0385(385),
        f0387(387),
        f0389(389),
        f0391(391),
        f0392(392),
        f0393(393),
        f0394(394),
        f0395(395),
        f0396(396),
        f0397(397),
        f0398(398),
        f0399(399),
        f0400(400),
        f0401(401),
        f0402(402),
        f0403(403),
        f0404(404),
        f0405(405),
        f0406(406),
        f0407(407),
        f0408(408),
        f0409(409),
        f0410(410),
        f0411(411),
        f0424(424),
        f0425(425),
        f0428(428),
        f0429(429),
        f0430(430),
        f0434(434),
        f0435(435),
        f0436(436),
        f0440(440),
        f0451(451),
        f0452(452),
        f0456(456),
        f0458(458),
        f0459(459),
        f0460(460),
        f0461(461),
        f0462(462),
        f0463(463),
        f0464(464),
        f0465(465),
        f0466(466),
        f0470(470),
        f0471(471),
        f0476(476),
        f0478(478),
        f0479(479),
        f0480(480),
        f0481(481),
        f0484(484),
        f0502(502),
        f0517(517),
        f0528(528),
        f0531(531),
        f0532(532),
        f0533(533),
        f0535(535),
        f0536(536),
        f0537(537),
        f0538(538),
        f0539(539),
        f0540(540),
        f0543(543),
        f0549(549),
        f0620(620),
        f0621(621),
        f0622(622),
        f0625(625),
        f0626(626),
        f0635(635),
        f0637(637),
        f0640(640),
        f0642(642),
        f0643(643),
        f0670(670),
        f0671(671),
        f0672(672),
        f0673(673),
        f0674(674),
        f0675(675),
        f0676(676),
        f0677(677),
        f0678(678),
        f0688(688),
        f0689(689),
        f0702(702),
        f0703(703),
        f0708(708),
        f0713(713),
        f0717(717),
        f0727(727),
        f0728(728),
        f0729(729),
        f0730(730),
        f0731(731),
        f0733(733),
        f0734(734),
        f0735(735),
        f0736(736),
        f0740(740),
        f0741(741),
        f0742(742),
        f0743(743),
        f0744(744),
        f0747(747),
        f0757(757),
        f0764(764),
        f0765(765),
        f0766(766),
        f0772(772),
        f0775(775),
        f0776(776),
        f0777(777),
        f0778(778),
        f0791(791),
        f0792(792),
        f0793(793),
        f0794(794),
        f16405(16405),
        f16406(16406),
        f16407(16407),
        f16408(16408),
        f16518(16518),
        f16519(16519),
        f16520(16520),
        f16533(16533),
        f16534(16534),
        f16535(16535),
        f16539(16539),
        f16550(16550),
        f16576(16576),
        f16577(16577),
        f16579(16579),
        f16580(16580),
        f16581(16581),
        f16582(16582),
        f16600(16600),
        f16601(16601),
        f16604(16604),
        f16605(16605),
        f16606(16606),
        f16634(16634),
        f16635(16635),
        f16636(16636),
        f16637(16637),
        f16641(16641),
        f16650(16650),
        f16651(16651),
        f16653(16653),
        f16654(16654),
        f16655(16655),
        f16656(16656),
        f16657(16657),
        f16670(16670),
        f16673(16673),
        f16674(16674),
        f16679(16679),
        f16680(16680),
        f16681(16681),
        f16682(16682),
        f16683(16683),
        f16684(16684),
        f16742(16742),
        f16745(16745),
        f16749(16749),
        f16750(16750),
        f16803(16803),
        f16815(16815),
        f16823(16823),
        f16852(16852),
        f16857(16857),
        f16858(16858),
        f16879(16879),
        f16880(16880),
        f16881(16881),
        f16898(16898),
        f16904(16904),
        f16906(16906),
        f16930(16930),
        f16931(16931),
        f16942(16942),
        f16943(16943),
        f16944(16944),
        f16945(16945),
        f16973(16973),
        f16974(16974),
        f16975(16975),
        f16976(16976),
        f16977(16977),
        f16978(16978),
        f16979(16979),
        f16980(16980),
        f16981(16981),
        f16982(16982),
        f16983(16983),
        f16984(16984),
        f16986(16986),
        f16987(16987),
        f16988(16988),
        f16994(16994),
        f16995(16995),
        f17000(17000),
        f17001(17001),
        f17002(17002),
        f17008(17008),
        f17012(17012),
        f17013(17013),
        f17014(17014),
        f17043(17043),
        f17044(17044),
        f17045(17045),
        f17046(17046),
        f17050(17050),
        f17051(17051),
        f17052(17052),
        f17053(17053),
        f17083(17083),
        f17084(17084),
        f17089(17089),
        f17116(17116),
        f17133(17133),
        f17134(17134),
        f17163(17163),
        f17169(17169),
        f17170(17170),
        f33142(33142),
        f33144(33144),
        f33145(33145),
        f33146(33146),
        f33167(33167),
        f33168(33168),
        f33169(33169),
        f33170(33170),
        f33177(33177),
        f33178(33178),
        f33179(33179),
        f33180(33180),
        f33187(33187),
        f33188(33188),
        f33189(33189),
        f33190(33190),
        f33197(33197),
        f33198(33198),
        f33199(33199),
        f33200(33200),
        f33211(33211),
        f33212(33212),
        f33213(33213),
        f33214(33214),
        f33221(33221),
        f33222(33222),
        f33223(33223),
        f33224(33224),
        f33231(33231),
        f33232(33232),
        f33233(33233),
        f33234(33234),
        f33241(33241),
        f33242(33242),
        f33243(33243),
        f33244(33244),
        f33251(33251),
        f33252(33252),
        f33253(33253),
        f33254(33254),
        f33261(33261),
        f33262(33262),
        f33263(33263),
        f33264(33264),
        f33271(33271),
        f33272(33272),
        f33273(33273),
        f33274(33274),
        f33281(33281),
        f33282(33282),
        f33283(33283),
        f33284(33284),
        f33291(33291),
        f33292(33292),
        f33293(33293),
        f33294(33294),
        f33301(33301),
        f33302(33302),
        f33303(33303),
        f33304(33304),
        f33483(33483),
        f33485(33485),
        f33486(33486),
        f33487(33487),
        f33491(33491),
        f33493(33493),
        f33494(33494),
        f33495(33495),
        f33499(33499),
        f33501(33501),
        f33502(33502),
        f33503(33503),
        f33720(33720),
        f33721(33721),
        f33722(33722),
        f33723(33723),
        f33730(33730),
        f33731(33731),
        f33732(33732),
        f33733(33733),
        f33740(33740),
        f33741(33741),
        f33742(33742),
        f33743(33743),
        f33750(33750),
        f33751(33751),
        f33752(33752),
        f33753(33753),
        f33760(33760),
        f33761(33761),
        f33762(33762),
        f33763(33763),
        f33770(33770),
        f33771(33771),
        f33772(33772),
        f33773(33773),
        f33810(33810),
        f33811(33811),
        f33812(33812),
        f33813(33813),
        f33820(33820),
        f33821(33821),
        f33822(33822),
        f33823(33823),
        f33830(33830),
        f33831(33831),
        f33832(33832),
        f33833(33833),
        f33840(33840),
        f33841(33841),
        f33842(33842),
        f33843(33843),
        f33850(33850),
        f33851(33851),
        f33852(33852),
        f33853(33853),
        f33860(33860),
        f33861(33861),
        f33862(33862),
        f33863(33863),
        f33875(33875),
        f33876(33876),
        f33877(33877),
        f33878(33878),
        f33885(33885),
        f33886(33886),
        f33887(33887),
        f33888(33888),
        f33895(33895),
        f33896(33896),
        f33897(33897),
        f33898(33898),
        f33905(33905),
        f33906(33906),
        f33907(33907),
        f33908(33908),
        f33915(33915),
        f33916(33916),
        f33917(33917),
        f33918(33918),
        f33925(33925),
        f33926(33926),
        f33927(33927),
        f33928(33928),
        f33940(33940),
        f33941(33941),
        f33942(33942),
        f33943(33943),
        f33950(33950),
        f33951(33951),
        f33952(33952),
        f33953(33953),
        f33960(33960),
        f33961(33961),
        f33962(33962),
        f33963(33963),
        f33970(33970),
        f33971(33971),
        f33972(33972),
        f33973(33973),
        f33980(33980),
        f33981(33981),
        f33982(33982),
        f33983(33983),
        f33995(33995),
        f33996(33996),
        f33997(33997),
        f33998(33998),
        f34005(34005),
        f34006(34006),
        f34007(34007),
        f34008(34008),
        f34015(34015),
        f34016(34016),
        f34017(34017),
        f34018(34018),
        f34030(34030),
        f34031(34031),
        f34032(34032),
        f34033(34033),
        f34040(34040),
        f34041(34041),
        f34042(34042),
        f34043(34043),
        f34050(34050),
        f34051(34051),
        f34052(34052),
        f34053(34053),
        f34064(34064),
        f34065(34065),
        f34066(34066),
        f34067(34067),
        f34074(34074),
        f34075(34075),
        f34076(34076),
        f34077(34077),
        f34084(34084),
        f34085(34085),
        f34086(34086),
        f34087(34087),
        f34094(34094),
        f34095(34095),
        f34096(34096),
        f34097(34097),
        f34108(34108),
        f34109(34109),
        f34110(34110),
        f34111(34111),
        f34118(34118),
        f34119(34119),
        f34120(34120),
        f34121(34121),
        f34128(34128),
        f34129(34129),
        f34130(34130),
        f34131(34131),
        f34138(34138),
        f34139(34139),
        f34140(34140),
        f34141(34141),
        f34148(34148),
        f34149(34149),
        f34150(34150),
        f34151(34151),
        f34158(34158),
        f34159(34159),
        f34160(34160),
        f34161(34161),
        f34168(34168),
        f34169(34169),
        f34170(34170),
        f34171(34171),
        f34178(34178),
        f34179(34179),
        f34180(34180),
        f34181(34181),
        f34192(34192),
        f34193(34193),
        f34194(34194),
        f34195(34195),
        f34202(34202),
        f34203(34203),
        f34204(34204),
        f34205(34205),
        f34212(34212),
        f34213(34213),
        f34214(34214),
        f34215(34215),
        f34222(34222),
        f34223(34223),
        f34224(34224),
        f34225(34225),
        f34232(34232),
        f34233(34233),
        f34234(34234),
        f34235(34235),
        f34246(34246),
        f34247(34247),
        f34248(34248),
        f34249(34249),
        f34256(34256),
        f34257(34257),
        f34258(34258),
        f34259(34259),
        f34271(34271),
        f34272(34272),
        f34273(34273),
        f34274(34274),
        f34281(34281),
        f34282(34282),
        f34283(34283),
        f34284(34284),
        f34291(34291),
        f34292(34292),
        f34293(34293),
        f34294(34294),
        f34301(34301),
        f34302(34302),
        f34303(34303),
        f34304(34304),
        f34316(34316),
        f34317(34317),
        f34318(34318),
        f34319(34319),
        f34326(34326),
        f34327(34327),
        f34328(34328),
        f34329(34329),
        f34336(34336),
        f34337(34337),
        f34338(34338),
        f34339(34339),
        f34346(34346),
        f34347(34347),
        f34348(34348),
        f34349(34349),
        f34361(34361),
        f34362(34362),
        f34363(34363),
        f34364(34364),
        f34371(34371),
        f34372(34372),
        f34373(34373),
        f34374(34374),
        f34381(34381),
        f34382(34382),
        f34383(34383),
        f34384(34384),
        f34396(34396),
        f34397(34397),
        f34398(34398),
        f34399(34399),
        f34406(34406),
        f34407(34407),
        f34408(34408),
        f34409(34409),
        f34416(34416),
        f34417(34417),
        f34418(34418),
        f34419(34419),
        f34426(34426),
        f34427(34427),
        f34428(34428),
        f34429(34429),
        f34436(34436),
        f34437(34437),
        f34438(34438),
        f34439(34439),
        f34451(34451),
        f34452(34452),
        f34453(34453),
        f34454(34454),
        f34461(34461),
        f34462(34462),
        f34463(34463),
        f34464(34464),
        f34471(34471),
        f34472(34472),
        f34473(34473),
        f34474(34474),
        f34481(34481),
        f34482(34482),
        f34483(34483),
        f34484(34484),
        f34496(34496),
        f34497(34497),
        f34498(34498),
        f34499(34499),
        f34506(34506),
        f34507(34507),
        f34508(34508),
        f34509(34509),
        f34516(34516),
        f34517(34517),
        f34518(34518),
        f34519(34519),
        f34526(34526),
        f34527(34527),
        f34528(34528),
        f34529(34529),
        f34542(34542),
        f34543(34543),
        f34544(34544),
        f34545(34545),
        f34552(34552),
        f34553(34553),
        f34554(34554),
        f34555(34555),
        f34562(34562),
        f34563(34563),
        f34564(34564),
        f34565(34565),
        f34572(34572),
        f34573(34573),
        f34574(34574),
        f34575(34575),
        f34588(34588),
        f34589(34589),
        f34590(34590),
        f34591(34591),
        f34598(34598),
        f34599(34599),
        f34600(34600),
        f34601(34601),
        f34608(34608),
        f34609(34609),
        f34610(34610),
        f34611(34611),
        f34618(34618),
        f34619(34619),
        f34620(34620),
        f34621(34621),
        f34633(34633),
        f34634(34634),
        f34635(34635),
        f34636(34636),
        f34643(34643),
        f34644(34644),
        f34645(34645),
        f34646(34646),
        f34653(34653),
        f34654(34654),
        f34655(34655),
        f34656(34656),
        f34663(34663),
        f34664(34664),
        f34665(34665),
        f34666(34666),
        f34673(34673),
        f34674(34674),
        f34675(34675),
        f34676(34676),
        f34688(34688),
        f34689(34689),
        f34690(34690),
        f34691(34691),
        f34698(34698),
        f34699(34699),
        f34700(34700),
        f34701(34701),
        f34708(34708),
        f34709(34709),
        f34710(34710),
        f34711(34711),
        f34718(34718),
        f34719(34719),
        f34720(34720),
        f34721(34721),
        f34733(34733),
        f34734(34734),
        f34735(34735),
        f34736(34736),
        f34743(34743),
        f34744(34744),
        f34745(34745),
        f34746(34746),
        f34753(34753),
        f34754(34754),
        f34755(34755),
        f34756(34756),
        f34763(34763),
        f34764(34764),
        f34765(34765),
        f34766(34766),
        f34778(34778),
        f34779(34779),
        f34780(34780),
        f34781(34781),
        f34788(34788),
        f34789(34789),
        f34790(34790),
        f34791(34791),
        f34798(34798),
        f34799(34799),
        f34800(34800),
        f34801(34801),
        f34808(34808),
        f34809(34809),
        f34810(34810),
        f34811(34811),
        f34822(34822),
        f34823(34823),
        f34824(34824),
        f34825(34825),
        f34832(34832),
        f34833(34833),
        f34834(34834),
        f34835(34835),
        f34842(34842),
        f34843(34843),
        f34844(34844),
        f34845(34845),
        f34852(34852),
        f34853(34853),
        f34854(34854),
        f34855(34855),
        f34862(34862),
        f34863(34863),
        f34864(34864),
        f34865(34865),
        f34872(34872),
        f34873(34873),
        f34874(34874),
        f34875(34875),
        f34882(34882),
        f34883(34883),
        f34884(34884),
        f34885(34885),
        f34892(34892),
        f34893(34893),
        f34894(34894),
        f34895(34895),
        f34906(34906),
        f34907(34907),
        f34908(34908),
        f34909(34909),
        f34916(34916),
        f34917(34917),
        f34918(34918),
        f34919(34919),
        f34926(34926),
        f34927(34927),
        f34928(34928),
        f34929(34929),
        f34936(34936),
        f34937(34937),
        f34938(34938),
        f34939(34939),
        f34950(34950),
        f34951(34951),
        f34952(34952),
        f34953(34953),
        f34960(34960),
        f34961(34961),
        f34962(34962),
        f34963(34963),
        f34970(34970),
        f34971(34971),
        f34972(34972),
        f34973(34973),
        f34980(34980),
        f34981(34981),
        f34982(34982),
        f34983(34983),
        f34990(34990),
        f34991(34991),
        f34992(34992),
        f34993(34993),
        f35000(35000),
        f35001(35001),
        f35002(35002),
        f35003(35003),
        f35010(35010),
        f35011(35011),
        f35012(35012),
        f35013(35013),
        f35020(35020),
        f35021(35021),
        f35022(35022),
        f35023(35023),
        f35166(35166),
        f35168(35168),
        f35169(35169),
        f35170(35170),
        f35174(35174),
        f35176(35176),
        f35177(35177),
        f35178(35178),
        f35198(35198),
        f35200(35200),
        f35201(35201),
        f35202(35202),
        f35206(35206),
        f35208(35208),
        f35209(35209),
        f35210(35210),
        f35214(35214),
        f35216(35216),
        f35217(35217),
        f35218(35218),
        f35222(35222),
        f35224(35224),
        f35225(35225),
        f35226(35226),
        f35234(35234),
        f35236(35236),
        f35237(35237),
        f35238(35238),
        f35242(35242),
        f35244(35244),
        f35245(35245),
        f35246(35246),
        f35250(35250),
        f35252(35252),
        f35253(35253),
        f35254(35254),
        f35275(35275),
        f35276(35276),
        f35277(35277),
        f35278(35278),
        f35285(35285),
        f35286(35286),
        f35287(35287),
        f35288(35288),
        f35295(35295),
        f35296(35296),
        f35297(35297),
        f35298(35298),
        f35305(35305),
        f35306(35306),
        f35307(35307),
        f35308(35308),
        f35315(35315),
        f35316(35316),
        f35317(35317),
        f35318(35318),
        f35329(35329),
        f35330(35330),
        f35331(35331),
        f35332(35332),
        f35339(35339),
        f35340(35340),
        f35341(35341),
        f35342(35342),
        f35349(35349),
        f35350(35350),
        f35351(35351),
        f35352(35352),
        f35359(35359),
        f35360(35360),
        f35361(35361),
        f35362(35362),
        f35369(35369),
        f35370(35370),
        f35371(35371),
        f35372(35372),
        f35379(35379),
        f35380(35380),
        f35381(35381),
        f35382(35382),
        f35962(35962),
        f35964(35964),
        f35965(35965),
        f35966(35966),
        f35974(35974),
        f35976(35976),
        f35977(35977),
        f35978(35978),
        f36234(36234),
        f36236(36236),
        f36237(36237),
        f36238(36238),
        f36242(36242),
        f36244(36244),
        f36245(36245),
        f36246(36246),
        f36266(36266),
        f36268(36268),
        f36269(36269),
        f36270(36270),
        f36274(36274),
        f36276(36276),
        f36277(36277),
        f36278(36278),
        f36282(36282),
        f36284(36284),
        f36285(36285),
        f36286(36286),
        f36294(36294),
        f36296(36296),
        f36297(36297),
        f36298(36298),
        f36302(36302),
        f36304(36304),
        f36305(36305),
        f36306(36306),
        f36310(36310),
        f36312(36312),
        f36313(36313),
        f36314(36314),
        f36323(36323),
        f36325(36325),
        f36326(36326),
        f36327(36327),
        f36335(36335),
        f36337(36337),
        f36338(36338),
        f36339(36339),
        f37154(37154),
        f37156(37156),
        f37157(37157),
        f37158(37158),
        f37162(37162),
        f37164(37164),
        f37165(37165),
        f37166(37166),
        f37170(37170),
        f37172(37172),
        f37173(37173),
        f37174(37174),
        f37269(37269),
        f37271(37271),
        f37272(37272),
        f37273(37273),
        f37313(37313),
        f37314(37314),
        f37315(37315),
        f37316(37316),
        f37323(37323),
        f37324(37324),
        f37325(37325),
        f37326(37326),
        f37333(37333),
        f37334(37334),
        f37335(37335),
        f37336(37336),
        f37343(37343),
        f37344(37344),
        f37345(37345),
        f37346(37346),
        f37353(37353),
        f37354(37354),
        f37355(37355),
        f37356(37356),
        f37363(37363),
        f37364(37364),
        f37365(37365),
        f37366(37366),
        f37383(37383),
        f37384(37384),
        f37385(37385),
        f37386(37386),
        f37393(37393),
        f37394(37394),
        f37395(37395),
        f37396(37396),
        f37403(37403),
        f37404(37404),
        f37405(37405),
        f37406(37406),
        f37413(37413),
        f37414(37414),
        f37415(37415),
        f37416(37416),
        f37423(37423),
        f37424(37424),
        f37425(37425),
        f37426(37426),
        f37443(37443),
        f37444(37444),
        f37445(37445),
        f37446(37446),
        f37453(37453),
        f37454(37454),
        f37455(37455),
        f37456(37456),
        f37463(37463),
        f37464(37464),
        f37465(37465),
        f37466(37466),
        f37473(37473),
        f37474(37474),
        f37475(37475),
        f37476(37476),
        f37485(37485),
        f37486(37486),
        f37487(37487),
        f37488(37488),
        f37495(37495),
        f37496(37496),
        f37497(37497),
        f37498(37498),
        f37505(37505),
        f37506(37506),
        f37507(37507),
        f37508(37508),
        f37532(37532),
        f37533(37533),
        f37534(37534),
        f37535(37535),
        f37543(37543),
        f37544(37544),
        f37545(37545),
        f37546(37546),
        f37553(37553),
        f37554(37554),
        f37555(37555),
        f37556(37556),
        f37564(37564),
        f37566(37566),
        f37567(37567),
        f37568(37568),
        f37572(37572),
        f37574(37574),
        f37575(37575),
        f37576(37576),
        f37580(37580),
        f37582(37582),
        f37583(37583),
        f37584(37584),
        f37600(37600),
        f37602(37602),
        f37603(37603),
        f37604(37604),
        f37610(37610),
        f37612(37612),
        f37613(37613),
        f37614(37614),
        f37771(37771),
        f37773(37773),
        f37774(37774),
        f37775(37775),
        f37779(37779),
        f37781(37781),
        f37782(37782),
        f37783(37783),
        f38022(38022),
        f38032(38032),
        f38044(38044),
        f38054(38054),
        f38064(38064),
        f38086(38086),
        f38096(38096),
        f38106(38106),
        f38128(38128),
        f38138(38138),
        f38148(38148),
        f38158(38158),
        f38311(38311),
        f38313(38313),
        f38314(38314),
        f38315(38315),
        f38349(38349),
        f38351(38351),
        f38352(38352),
        f38353(38353),
        f38357(38357),
        f38359(38359),
        f38360(38360),
        f38361(38361),
        f38408(38408),
        f38409(38409),
        f38410(38410),
        f38411(38411),
        f38438(38438),
        f38440(38440),
        f38441(38441),
        f38442(38442),
        f38451(38451),
        f38453(38453),
        f38454(38454),
        f38455(38455),
        f38779(38779),
        f38788(38788),
        f38797(38797),
        f38806(38806),
        f38815(38815),
        f38829(38829),
        f38838(38838),
        f38847(38847),
        f38856(38856),
        f38909(38909),
        f39032(39032),
        f39034(39034),
        f39035(39035),
        f39036(39036),
        f39040(39040),
        f39042(39042),
        f39043(39043),
        f39044(39044),
        f39240(39240),
        f39242(39242),
        f39243(39243),
        f39244(39244),
        f39421(39421),
        f39423(39423),
        f39424(39424),
        f39425(39425),
        f39429(39429),
        f39431(39431),
        f39432(39432),
        f39433(39433),
        f39437(39437),
        f39439(39439),
        f39440(39440),
        f39441(39441),
        f39445(39445),
        f39447(39447),
        f39448(39448),
        f39449(39449),
        f39453(39453),
        f39455(39455),
        f39456(39456),
        f39457(39457),
        f39464(39464),
        f39466(39466),
        f39467(39467),
        f39468(39468),
        f39472(39472),
        f39474(39474),
        f39475(39475),
        f39476(39476),
        f39480(39480),
        f39482(39482),
        f39483(39483),
        f39484(39484),
        f39488(39488),
        f39490(39490),
        f39491(39491),
        f39492(39492),
        f39498(39498),
        f39500(39500),
        f39501(39501),
        f39502(39502),
        f39506(39506),
        f39508(39508),
        f39509(39509),
        f39510(39510),
        f39514(39514),
        f39516(39516),
        f39517(39517),
        f39518(39518),
        f39525(39525),
        f39527(39527),
        f39528(39528),
        f39529(39529),
        f39533(39533),
        f39535(39535),
        f39536(39536),
        f39537(39537),
        f39541(39541),
        f39543(39543),
        f39544(39544),
        f39545(39545),
        f39549(39549),
        f39551(39551),
        f39552(39552),
        f39553(39553),
        f39557(39557),
        f39559(39559),
        f39560(39560),
        f39561(39561),
        f39565(39565),
        f39567(39567),
        f39568(39568),
        f39569(39569),
        f39575(39575),
        f39577(39577),
        f39578(39578),
        f39579(39579),
        f40092(40092),
        f40094(40094),
        f40095(40095),
        f40096(40096),
        f40100(40100),
        f40102(40102),
        f40103(40103),
        f40104(40104),
        f40108(40108),
        f40110(40110),
        f40111(40111),
        f40112(40112),
        f40116(40116),
        f40118(40118),
        f40119(40119),
        f40120(40120),
        f40124(40124),
        f40126(40126),
        f40127(40127),
        f40128(40128),
        f77845(77845),
        f77846(77846),
        f77847(77847),
        f77848(77848),
        f77958(77958),
        f77959(77959),
        f77960(77960),
        f77973(77973),
        f77974(77974),
        f77975(77975),
        f77979(77979),
        f77990(77990),
        f78016(78016),
        f78017(78017),
        f78019(78019),
        f78020(78020),
        f78021(78021),
        f78022(78022),
        f78040(78040),
        f78041(78041),
        f78044(78044),
        f78045(78045),
        f78046(78046),
        f78074(78074),
        f78075(78075),
        f78076(78076),
        f78077(78077),
        f78081(78081),
        f78090(78090),
        f78091(78091),
        f78093(78093),
        f78094(78094),
        f78095(78095),
        f78096(78096),
        f78097(78097),
        f78110(78110),
        f78113(78113),
        f78114(78114),
        f78119(78119),
        f78120(78120),
        f78121(78121),
        f78122(78122),
        f78123(78123),
        f78124(78124),
        f78182(78182),
        f78185(78185),
        f78189(78189),
        f78190(78190),
        f78243(78243),
        f78255(78255),
        f78263(78263),
        f78292(78292),
        f78297(78297),
        f78298(78298),
        f78319(78319),
        f78320(78320),
        f78321(78321),
        f78338(78338),
        f78344(78344),
        f78346(78346),
        f78370(78370),
        f78371(78371),
        f78382(78382),
        f78383(78383),
        f78384(78384),
        f78385(78385),
        f78413(78413),
        f78414(78414),
        f78415(78415),
        f78416(78416),
        f78417(78417),
        f78418(78418),
        f78419(78419),
        f78420(78420),
        f78421(78421),
        f78422(78422),
        f78423(78423),
        f78424(78424),
        f78426(78426),
        f78427(78427),
        f78428(78428),
        f78434(78434),
        f78435(78435),
        f78440(78440),
        f78441(78441),
        f78442(78442),
        f78448(78448),
        f78452(78452),
        f78453(78453),
        f78454(78454),
        f78483(78483),
        f78484(78484),
        f78485(78485),
        f78486(78486),
        f78490(78490),
        f78491(78491),
        f78492(78492),
        f78493(78493),
        f78523(78523),
        f78524(78524),
        f78529(78529),
        f78556(78556),
        f78573(78573),
        f78574(78574),
        f78603(78603),
        f78609(78609),
        f78610(78610),
        f999445(999445),
        f999446(999446),
        f999447(999447),
        f999448(999448),
        f999558(999558),
        f999559(999559),
        f999560(999560),
        f999573(999573),
        f999574(999574),
        f999575(999575),
        f999579(999579),
        f999590(999590),
        f999616(999616),
        f999617(999617),
        f999619(999619),
        f999620(999620),
        f999621(999621),
        f999622(999622),
        f999640(999640),
        f999641(999641),
        f999644(999644),
        f999645(999645),
        f999646(999646),
        f999674(999674),
        f999675(999675),
        f999676(999676),
        f999677(999677),
        f999681(999681),
        f999690(999690),
        f999691(999691),
        f999693(999693),
        f999694(999694),
        f999695(999695),
        f999696(999696),
        f999697(999697),
        f999710(999710),
        f999713(999713),
        f999714(999714),
        f999719(999719),
        f999720(999720),
        f999721(999721),
        f999722(999722),
        f999723(999723),
        f999724(999724),
        f999782(999782),
        f999785(999785),
        f999789(999789),
        f999790(999790),
        f999843(999843),
        f999855(999855),
        f999863(999863),
        f999892(999892),
        f999897(999897),
        f999898(999898),
        f999919(999919),
        f999920(999920),
        f999921(999921),
        f999938(999938),
        f999944(999944),
        f999946(999946),
        f999970(999970),
        f999971(999971),
        f999982(999982),
        f999983(999983),
        f999984(999984),
        f999985(999985),
        f1000013(1000013),
        f1000014(1000014),
        f1000015(1000015),
        f1000016(1000016),
        f1000017(1000017),
        f1000018(1000018),
        f1000019(1000019),
        f1000020(1000020),
        f1000021(1000021),
        f1000022(1000022),
        f1000023(1000023),
        f1000024(1000024),
        f1000026(1000026),
        f1000027(1000027),
        f1000028(1000028),
        f1000034(1000034),
        f1000035(1000035),
        f1000040(1000040),
        f1000041(1000041),
        f1000042(1000042),
        f1000048(1000048),
        f1000052(1000052),
        f1000053(1000053),
        f1000054(1000054),
        f1000083(1000083),
        f1000084(1000084),
        f1000085(1000085),
        f1000086(1000086),
        f1000090(1000090),
        f1000091(1000091),
        f1000092(1000092),
        f1000093(1000093),
        f1000123(1000123),
        f1000124(1000124),
        f1000129(1000129),
        f1000156(1000156),
        f1000173(1000173),
        f1000174(1000174),
        f1000203(1000203),
        f1000209(1000209),
        f1000210(1000210),
        e4194528(4194528),
        e4194529(4194529),
        e4194530(4194530),
        e4194531(4194531),
        e4194532(4194532),
        e4194533(4194533),
        e4194534(4194534),
        e4194535(4194535),
        e4194536(4194536),
        e4194537(4194537),
        e4194538(4194538),
        e4194539(4194539),
        e4194540(4194540),
        e4194541(4194541),
        e4194542(4194542),
        e4194543(4194543),
        e4194544(4194544),
        e4194545(4194545),
        e4194546(4194546),
        e4194547(4194547),
        e4194548(4194548),
        e4194549(4194549),
        e4194550(4194550),
        e4194551(4194551),
        e4194552(4194552),
        e4194553(4194553),
        e4194554(4194554),
        e4194555(4194555),
        e4194556(4194556),
        e4194557(4194557),
        e4194558(4194558),
        e4194559(4194559),
        e4194560(4194560),
        e4194561(4194561),
        e4194562(4194562),
        e4194563(4194563),
        e4194564(4194564),
        e4194565(4194565),
        e4194566(4194566),
        e4194567(4194567),
        e4194568(4194568),
        e4194569(4194569),
        e4194570(4194570),
        e4194571(4194571),
        e4194572(4194572),
        e4194573(4194573),
        e4194574(4194574),
        e4194575(4194575),
        e4194576(4194576),
        e4194577(4194577),
        e4194578(4194578),
        e4194579(4194579),
        e4194580(4194580),
        e4194581(4194581),
        e4194582(4194582),
        e4194583(4194583),
        e4194584(4194584),
        e4194585(4194585),
        e4194586(4194586),
        e4194587(4194587),
        e4194591(4194591),
        e4194592(4194592),
        e4194593(4194593),
        e4194594(4194594),
        e4194595(4194595),
        e4194596(4194596),
        e4194597(4194597),
        e4194598(4194598),
        e4194599(4194599),
        e4194600(4194600),
        e4194601(4194601),
        e4194602(4194602),
        e4194603(4194603),
        e4194604(4194604),
        e4194605(4194605),
        e4194607(4194607),
        e4194608(4194608),
        e4194609(4194609),
        e4194610(4194610),
        e4194611(4194611),
        e4194612(4194612),
        e4194613(4194613),
        e4194614(4194614),
        e4194615(4194615),
        e4194616(4194616),
        e4194617(4194617),
        e4194620(4194620),
        e4194621(4194621),
        e4194622(4194622),
        e4194623(4194623),
        e4194624(4194624),
        e4194626(4194626),
        e4194627(4194627),
        e4194628(4194628),
        e4194629(4194629),
        e4194630(4194630),
        e4194631(4194631),
        e4194632(4194632),
        e4194652(4194652),
        e4194654(4194654),
        e4194655(4194655),
        e4194656(4194656),
        e4194657(4194657),
        e4194658(4194658),
        e4194659(4194659),
        e4194660(4194660),
        e4194661(4194661),
        e4194662(4194662),
        e4194663(4194663),
        e4194664(4194664),
        e4194665(4194665),
        e4194671(4194671),
        e4194672(4194672),
        e4194673(4194673),
        e4194674(4194674),
        e4194675(4194675),
        e4194676(4194676),
        e4194683(4194683),
        e4194684(4194684),
        e4194685(4194685),
        e4194686(4194686),
        e4194687(4194687),
        e4194688(4194688),
        e4194689(4194689),
        e4194693(4194693),
        e4194694(4194694),
        e4194695(4194695),
        e4194697(4194697),
        e4194698(4194698),
        e4194699(4194699),
        e4194700(4194700),
        e4194701(4194701),
        e4194702(4194702),
        e4194703(4194703),
        e4194704(4194704),
        e4194705(4194705),
        e4194706(4194706),
        e4194714(4194714),
        e4194715(4194715),
        e4194717(4194717),
        e4194718(4194718),
        e4194719(4194719),
        e4194720(4194720),
        e4194721(4194721),
        e4194722(4194722),
        e4194723(4194723),
        e4194724(4194724),
        e4194725(4194725),
        e4194726(4194726),
        e4194727(4194727),
        e4194728(4194728),
        e4194729(4194729),
        e4194730(4194730),
        e4194734(4194734),
        e4194736(4194736),
        e4194737(4194737),
        e4194738(4194738),
        e4194739(4194739),
        e4194740(4194740),
        e4194741(4194741),
        e4194744(4194744),
        e4194745(4194745),
        e4194746(4194746),
        e4194747(4194747),
        e4194748(4194748),
        e4194749(4194749),
        e4194750(4194750),
        e4194751(4194751),
        e4194752(4194752),
        e4194753(4194753),
        e4194754(4194754),
        e4194755(4194755),
        e4194763(4194763),
        e4194764(4194764),
        e4194765(4194765),
        e4194766(4194766),
        e4194767(4194767),
        e4194768(4194768),
        e4194769(4194769),
        e4194770(4194770),
        e4194771(4194771),
        e4194773(4194773),
        e4194774(4194774),
        e4194775(4194775),
        e4194776(4194776),
        e4194777(4194777),
        e4194778(4194778),
        e4194787(4194787),
        e4194788(4194788),
        e4194789(4194789),
        e4194790(4194790),
        e4194791(4194791),
        e4194792(4194792),
        e4194793(4194793),
        e4194794(4194794),
        e4194795(4194795),
        e4194796(4194796),
        e4194797(4194797),
        e4194798(4194798),
        e4194799(4194799),
        e4194800(4194800),
        e4194801(4194801),
        e4194802(4194802),
        e4194803(4194803),
        e4194804(4194804),
        e4194805(4194805),
        e4194806(4194806),
        e4194807(4194807),
        e4194812(4194812),
        e4194828(4194828),
        e4194830(4194830),
        e4194831(4194831),
        e4194832(4194832),
        e4194833(4194833),
        e4194834(4194834),
        e4194835(4194835),
        e4194836(4194836),
        e4194847(4194847),
        e4194848(4194848),
        e4194849(4194849),
        e4194855(4194855),
        e4194856(4194856),
        e4194859(4194859),
        e4194860(4194860),
        e4194861(4194861),
        e4194862(4194862),
        e4194863(4194863),
        e4194864(4194864),
        e4194865(4194865),
        e4194866(4194866),
        e4194867(4194867),
        e4194868(4194868),
        e4194869(4194869),
        e4194871(4194871),
        e4194876(4194876),
        e4194878(4194878),
        e4194879(4194879),
        e4194880(4194880),
        e4194881(4194881),
        e4194883(4194883),
        e4194884(4194884),
        e4194885(4194885),
        e4194886(4194886),
        e4194887(4194887),
        e4194888(4194888),
        e4194889(4194889),
        e4194890(4194890),
        e4194891(4194891),
        e4194892(4194892),
        e4194894(4194894),
        e4194895(4194895),
        e4194896(4194896),
        e4194897(4194897),
        e4194899(4194899),
        e4194900(4194900),
        e4194901(4194901),
        e4194902(4194902),
        e4194903(4194903),
        e4194904(4194904),
        e4194905(4194905),
        e4194906(4194906),
        e4194907(4194907),
        e4194908(4194908),
        e4194909(4194909),
        e4194910(4194910),
        e4194911(4194911),
        e4194918(4194918),
        e4194919(4194919),
        e4194920(4194920),
        e4194921(4194921),
        e4194922(4194922),
        e4194923(4194923),
        e4194924(4194924),
        e4194925(4194925),
        e4194926(4194926),
        e4194927(4194927),
        e4194928(4194928),
        e4194929(4194929),
        e4194930(4194930),
        e4194931(4194931),
        e4194932(4194932),
        e4194933(4194933),
        e4194934(4194934),
        e4194935(4194935),
        e4194936(4194936),
        e4194937(4194937),
        e4194938(4194938),
        e4194939(4194939),
        e4194940(4194940),
        e4194941(4194941),
        e4194942(4194942),
        e4194943(4194943),
        e4194944(4194944),
        e4194945(4194945),
        e4194946(4194946),
        e4194947(4194947),
        e4194948(4194948),
        e4194949(4194949),
        e4194950(4194950),
        e4194951(4194951),
        e4194952(4194952),
        e4194953(4194953),
        e4194954(4194954),
        e4194955(4194955),
        e4194956(4194956),
        e4194969(4194969),
        e4194970(4194970),
        e4194971(4194971),
        e4194975(4194975),
        e4194976(4194976),
        e4194977(4194977),
        e4194978(4194978),
        e4194979(4194979),
        e4194980(4194980),
        e4194981(4194981),
        e4194982(4194982),
        e4194983(4194983),
        e4194984(4194984),
        e4194985(4194985),
        e4194986(4194986),
        e4194987(4194987),
        e4194988(4194988),
        e4194989(4194989),
        e4194990(4194990),
        e4194991(4194991),
        e4194992(4194992),
        e4194993(4194993),
        e4194994(4194994),
        e4194995(4194995),
        e4194996(4194996),
        e4194997(4194997),
        e4195000(4195000),
        e4195001(4195001),
        e4195002(4195002),
        e4195003(4195003),
        e4195004(4195004),
        e4195006(4195006),
        e4195007(4195007),
        e4195008(4195008),
        e4195009(4195009),
        e4195010(4195010),
        e4195011(4195011),
        e4195012(4195012),
        e4195013(4195013),
        e4195014(4195014),
        e4195015(4195015),
        e4195016(4195016),
        e4195017(4195017),
        e4195018(4195018),
        e4195019(4195019),
        e4195020(4195020),
        e4195021(4195021),
        e4195022(4195022),
        e4195023(4195023),
        e4195024(4195024),
        e4195025(4195025),
        e4195026(4195026),
        e4195027(4195027),
        e4195028(4195028),
        e4195029(4195029),
        e4195030(4195030),
        e4195031(4195031),
        e4195032(4195032),
        e4195033(4195033),
        e4195034(4195034),
        e4195036(4195036),
        e4195037(4195037),
        e4195038(4195038),
        e4195039(4195039),
        e4195040(4195040),
        e4195041(4195041),
        e4195042(4195042),
        e4195043(4195043),
        e4195044(4195044),
        e4195045(4195045),
        e4195046(4195046),
        e4195047(4195047),
        e4195048(4195048),
        e4195049(4195049),
        e4195050(4195050),
        e4195051(4195051),
        e4195052(4195052),
        e4195053(4195053),
        e4195054(4195054),
        e4195055(4195055),
        e4195056(4195056),
        e4195057(4195057),
        e4195058(4195058),
        e4195059(4195059),
        e4195060(4195060),
        e4195061(4195061),
        e4195064(4195064),
        e4195065(4195065),
        e4195066(4195066),
        e4195067(4195067),
        e4195068(4195068),
        e4195069(4195069),
        e4195071(4195071),
        e4195072(4195072),
        e4195073(4195073),
        e4195074(4195074),
        e4195075(4195075),
        e4195076(4195076),
        e4195077(4195077),
        e4195078(4195078),
        e4195080(4195080),
        e4195081(4195081),
        e4195082(4195082),
        e4195083(4195083),
        e4195084(4195084),
        e4195085(4195085),
        e4195086(4195086),
        e4195087(4195087),
        e4195088(4195088),
        e4195207(4195207),
        e4195208(4195208),
        e4195209(4195209),
        e4195213(4195213),
        e4195214(4195214),
        e4195220(4195220),
        e4195221(4195221),
        e4195222(4195222),
        e4195223(4195223),
        e4195224(4195224),
        e4195225(4195225),
        e4195226(4195226),
        e4195227(4195227),
        e4195228(4195228),
        e4195229(4195229),
        e4195230(4195230),
        e4195231(4195231),
        e4195232(4195232),
        e4195233(4195233),
        e4195234(4195234),
        e4195235(4195235),
        e4195236(4195236),
        e4195237(4195237),
        e4195238(4195238),
        e4195239(4195239),
        e4195242(4195242),
        e4195243(4195243),
        e4195244(4195244),
        e4195245(4195245),
        e4195246(4195246),
        e4195247(4195247),
        e4195248(4195248),
        e4195249(4195249),
        e4195250(4195250),
        e4195251(4195251),
        e4195252(4195252),
        e4195253(4195253),
        e4195254(4195254),
        e4195255(4195255),
        e4195256(4195256),
        e4195257(4195257),
        e4195258(4195258),
        e4195259(4195259),
        e4195260(4195260),
        e4195261(4195261),
        e4195262(4195262),
        e4195263(4195263),
        e4195264(4195264),
        e4195265(4195265),
        e4195266(4195266),
        e4195267(4195267),
        e4195268(4195268),
        e4195269(4195269),
        e4195270(4195270),
        e4195271(4195271),
        e4195272(4195272),
        e4195273(4195273),
        e4195274(4195274),
        e4195275(4195275),
        e4195276(4195276),
        e4195277(4195277),
        e4195278(4195278),
        e4195279(4195279),
        e4195281(4195281),
        e4195282(4195282),
        e4195283(4195283),
        e4195284(4195284),
        e4195285(4195285),
        e4195286(4195286),
        e4195287(4195287),
        e4195288(4195288),
        e4195289(4195289),
        e4195290(4195290),
        e4195291(4195291),
        e4195292(4195292),
        e4195293(4195293),
        e4195294(4195294),
        e4195295(4195295),
        e4195296(4195296),
        e4195297(4195297),
        e4195298(4195298),
        e4195299(4195299),
        e4195300(4195300),
        e4195301(4195301),
        e4195302(4195302),
        e4195303(4195303),
        e4195304(4195304),
        e4195305(4195305),
        e4195306(4195306),
        e4195307(4195307),
        e4195308(4195308),
        e4195309(4195309),
        e4195310(4195310),
        e4195311(4195311),
        e4195312(4195312),
        e4195313(4195313),
        e4195314(4195314),
        e4195315(4195315),
        e4195316(4195316),
        e4195317(4195317),
        e4195318(4195318),
        e4195319(4195319),
        e4195320(4195320),
        e4195321(4195321),
        e4195331(4195331),
        e4195332(4195332),
        e4195333(4195333),
        e4195334(4195334),
        e4195335(4195335),
        e4195336(4195336),
        e4195337(4195337),
        e4195338(4195338),
        e4195339(4195339),
        e4195340(4195340),
        e4195341(4195341),
        e4195342(4195342),
        e4195343(4195343),
        e4195344(4195344),
        e4195345(4195345),
        e4195346(4195346),
        e4195347(4195347),
        e4195348(4195348),
        e4195349(4195349),
        e4195350(4195350),
        e4195351(4195351),
        e4195352(4195352),
        e4195353(4195353),
        e4195354(4195354),
        e4195355(4195355),
        e4195356(4195356),
        e4195357(4195357),
        e4195358(4195358),
        e4195359(4195359),
        e4195360(4195360),
        e4195361(4195361),
        e4195362(4195362),
        e4195363(4195363),
        e4195364(4195364),
        e4195365(4195365),
        e4195366(4195366),
        e4195367(4195367),
        e4195368(4195368),
        e4195369(4195369),
        e4195370(4195370),
        e4195371(4195371),
        e4195372(4195372),
        e4195373(4195373),
        e4195374(4195374),
        e4195375(4195375),
        e4195376(4195376),
        e4195377(4195377),
        e4195378(4195378),
        e4195379(4195379),
        e4195380(4195380),
        e4195381(4195381),
        e4195382(4195382),
        e4195387(4195387),
        e4195388(4195388),
        e4195389(4195389),
        e4195390(4195390),
        e4195391(4195391),
        e4195392(4195392),
        e4195393(4195393),
        e4195394(4195394),
        e4195395(4195395),
        e4195396(4195396),
        e4195397(4195397),
        e4195398(4195398),
        e4195399(4195399),
        e4195400(4195400),
        e4195401(4195401),
        e4195402(4195402),
        e4195403(4195403),
        e4195404(4195404),
        e4195405(4195405),
        e4195406(4195406),
        e4195407(4195407),
        e4195408(4195408),
        e4195409(4195409),
        e4195410(4195410),
        e4195411(4195411),
        e4195412(4195412),
        e4195413(4195413),
        e4195414(4195414),
        e4195415(4195415),
        e4195416(4195416),
        e4195417(4195417),
        e4195418(4195418),
        e4195419(4195419),
        e4195460(4195460),
        e4195461(4195461),
        e4195462(4195462),
        e4195463(4195463),
        e4195464(4195464),
        e4195465(4195465),
        e4195466(4195466),
        e4195467(4195467),
        e4195468(4195468),
        e4195469(4195469),
        e4195470(4195470),
        e4195471(4195471),
        e4195472(4195472),
        e4195473(4195473),
        e4195474(4195474),
        e4195475(4195475),
        e4195476(4195476),
        e4195477(4195477),
        e4195478(4195478),
        e4195479(4195479),
        e4195480(4195480),
        e4195481(4195481),
        e4195482(4195482),
        e4195483(4195483),
        e4195484(4195484),
        e4195485(4195485),
        e4195486(4195486),
        e4195487(4195487),
        e4195488(4195488),
        e4195489(4195489),
        e4195490(4195490),
        e4195491(4195491),
        e4195492(4195492),
        e4195493(4195493),
        e4195494(4195494),
        e4195495(4195495),
        e4195496(4195496),
        e4195497(4195497),
        e4195498(4195498),
        e4195499(4195499),
        e4195500(4195500),
        e4195501(4195501),
        e4195502(4195502),
        e4195503(4195503),
        e4195504(4195504),
        e4195505(4195505),
        e4195506(4195506),
        e4195507(4195507),
        e4195508(4195508),
        e4195509(4195509),
        e4195510(4195510),
        e4195511(4195511),
        e4195512(4195512),
        e4195513(4195513),
        e4195514(4195514),
        e4195515(4195515),
        e4195516(4195516),
        e4195517(4195517),
        e4195518(4195518),
        e4195519(4195519),
        e4195520(4195520),
        e4195521(4195521),
        e4195522(4195522),
        e4195523(4195523),
        e4195524(4195524),
        e4195525(4195525),
        e4195526(4195526),
        e4195527(4195527),
        e4195528(4195528),
        e4195529(4195529),
        e4195530(4195530),
        e4195531(4195531),
        e4195532(4195532),
        e4195533(4195533),
        e4195534(4195534),
        e4195535(4195535),
        e4195536(4195536),
        e4195537(4195537),
        e4195538(4195538),
        e4195539(4195539),
        e4195540(4195540),
        e4195541(4195541),
        e4195542(4195542),
        e4195543(4195543),
        e4195544(4195544),
        e4195545(4195545),
        e4195546(4195546),
        e4195547(4195547),
        e4195548(4195548),
        e4195549(4195549),
        e4195550(4195550),
        e4195551(4195551),
        e4195552(4195552),
        e4195553(4195553),
        e4195554(4195554),
        e4195558(4195558),
        e4195559(4195559),
        e4195560(4195560),
        e4195561(4195561),
        e4195562(4195562),
        e4195563(4195563),
        e4195564(4195564),
        e4195565(4195565),
        e4195566(4195566),
        e4195567(4195567),
        e4195568(4195568),
        e4195571(4195571),
        e4195572(4195572),
        e4195573(4195573),
        e4195574(4195574),
        e4195575(4195575),
        e4195576(4195576),
        e4195577(4195577),
        e4195578(4195578),
        e4195579(4195579),
        e4195580(4195580),
        e4195581(4195581),
        e4195582(4195582),
        e4195583(4195583),
        e4195584(4195584),
        e4195585(4195585),
        e4195586(4195586),
        e4195587(4195587),
        e4195588(4195588),
        e4195592(4195592),
        e4195593(4195593),
        e4195594(4195594),
        e4195595(4195595),
        e4195596(4195596),
        e4195597(4195597),
        e4195598(4195598),
        e4195599(4195599),
        e4195601(4195601),
        e4195602(4195602),
        e4195603(4195603),
        e4195604(4195604),
        e4195605(4195605),
        e4195606(4195606),
        e4195607(4195607),
        e4195615(4195615),
        e4195616(4195616),
        e4195617(4195617),
        e4195655(4195655),
        e4195656(4195656),
        e4195660(4195660),
        e4195661(4195661),
        e4195662(4195662),
        e4195663(4195663),
        e4195664(4195664),
        e4195665(4195665),
        e4195666(4195666),
        e4195667(4195667),
        e4195669(4195669),
        e4195670(4195670),
        e4195671(4195671),
        e4195672(4195672),
        e4195673(4195673),
        e4195674(4195674),
        e4195698(4195698),
        e4195699(4195699),
        e4195700(4195700),
        e4195701(4195701),
        e4195702(4195702),
        e4195703(4195703),
        e4195704(4195704),
        e4195705(4195705),
        e4195706(4195706),
        e4195707(4195707),
        e4195708(4195708),
        e4195709(4195709),
        e4195710(4195710),
        e4195711(4195711),
        e4195712(4195712),
        e4195713(4195713),
        e4195714(4195714),
        e4195715(4195715),
        e4195716(4195716),
        e4195718(4195718),
        e4195721(4195721),
        e4195730(4195730),
        e4195731(4195731),
        e4195732(4195732),
        e4195733(4195733),
        e4195734(4195734),
        e4195735(4195735),
        e4195736(4195736),
        e4195737(4195737),
        e4195738(4195738),
        e4195739(4195739),
        e4195740(4195740),
        e4195741(4195741),
        e4195742(4195742),
        e4195743(4195743),
        e4195744(4195744),
        e4195745(4195745),
        e4195746(4195746),
        e4195747(4195747),
        e4195748(4195748),
        e4195749(4195749),
        e4195750(4195750),
        e4195751(4195751),
        e4195752(4195752),
        e4195753(4195753),
        e4195754(4195754),
        e4195755(4195755),
        e4195756(4195756),
        e4195757(4195757),
        e4195758(4195758),
        e4195759(4195759),
        e4195760(4195760),
        e4195761(4195761),
        e4195762(4195762),
        e4195763(4195763),
        e4195764(4195764),
        e4195765(4195765),
        e4195766(4195766),
        e4195767(4195767),
        e4195768(4195768),
        e4195769(4195769),
        e4195770(4195770),
        e4195771(4195771),
        e4195772(4195772),
        e4195773(4195773),
        e4195774(4195774),
        e4195775(4195775),
        e4195776(4195776),
        e4195777(4195777),
        e4195778(4195778),
        e4195779(4195779),
        e4195786(4195786),
        e4195787(4195787),
        e4195788(4195788),
        e4195789(4195789),
        e4195790(4195790),
        e4195791(4195791),
        e4195792(4195792),
        e4195793(4195793),
        e4195794(4195794),
        e4195795(4195795),
        e4195796(4195796),
        e4195797(4195797),
        e4195798(4195798),
        e4195799(4195799),
        e4195800(4195800),
        e4195801(4195801),
        e4195802(4195802),
        e4195803(4195803),
        e4195804(4195804),
        e4195807(4195807),
        e4195808(4195808),
        e4195809(4195809),
        e4195810(4195810),
        e4195811(4195811),
        e4195812(4195812),
        e4195813(4195813),
        e4195814(4195814),
        e4195815(4195815),
        e4195818(4195818),
        e4195819(4195819),
        e4195820(4195820),
        e4195821(4195821),
        e4195822(4195822),
        e4195823(4195823),
        e4195824(4195824),
        e4195825(4195825),
        e4195826(4195826),
        e4195827(4195827),
        e4195828(4195828),
        e4195829(4195829),
        e4195830(4195830),
        e4195831(4195831),
        e4195832(4195832),
        e4195833(4195833),
        e4195834(4195834),
        e4195835(4195835),
        e4195836(4195836),
        e4195837(4195837),
        e4195838(4195838),
        e4195839(4195839),
        e4195840(4195840),
        e4195841(4195841),
        e4195842(4195842),
        e4195843(4195843),
        e4195844(4195844),
        e4195845(4195845),
        e4195846(4195846),
        e4195847(4195847),
        e4195848(4195848),
        e4195849(4195849),
        e4195850(4195850),
        e4195851(4195851),
        e4195852(4195852),
        e4195853(4195853),
        e4195854(4195854),
        e4195855(4195855),
        e4195856(4195856),
        e4195857(4195857),
        e4195858(4195858),
        e4195859(4195859),
        e4195860(4195860),
        e4195861(4195861),
        e4195862(4195862),
        e4195863(4195863),
        e4195864(4195864),
        e4195865(4195865),
        e4195866(4195866),
        e4195867(4195867),
        e4195868(4195868),
        e4195869(4195869),
        e4195870(4195870),
        e4195871(4195871),
        e4195872(4195872),
        e4195873(4195873),
        e4195874(4195874),
        e4195875(4195875),
        e4195876(4195876),
        e4195877(4195877),
        e4195880(4195880),
        e4195881(4195881),
        e4195882(4195882),
        e4195883(4195883),
        e4195884(4195884),
        e4195885(4195885),
        e4195886(4195886),
        e4195887(4195887),
        e4195888(4195888),
        e4195889(4195889),
        e4195890(4195890),
        e4195891(4195891),
        e4195892(4195892),
        e4195893(4195893),
        e4195894(4195894),
        e4195895(4195895),
        e4195896(4195896),
        e4195897(4195897),
        e4195898(4195898),
        e4195899(4195899),
        e4195900(4195900),
        e4195901(4195901),
        e4195902(4195902),
        e4195903(4195903),
        e4195904(4195904),
        e4195905(4195905),
        e4195906(4195906),
        e4195907(4195907),
        e4195908(4195908),
        e4195909(4195909),
        e4195910(4195910),
        e4195911(4195911),
        e4195912(4195912),
        e4195913(4195913),
        e4195914(4195914),
        e4195915(4195915),
        e4195916(4195916),
        e4195917(4195917),
        e4195918(4195918),
        e4195919(4195919),
        e4195920(4195920),
        e4195921(4195921),
        e4195922(4195922),
        e4195923(4195923),
        e4195924(4195924),
        e4195925(4195925),
        e4195926(4195926),
        e4195927(4195927),
        e4195928(4195928),
        e4195929(4195929),
        e4195930(4195930),
        e4195931(4195931),
        e4195932(4195932),
        e4195933(4195933),
        e4195934(4195934),
        e4195935(4195935),
        e4195936(4195936),
        e4195937(4195937),
        e4195938(4195938),
        e4195939(4195939),
        e4195940(4195940),
        e4195941(4195941),
        e4195942(4195942),
        e4195943(4195943),
        e4195944(4195944),
        e4195945(4195945),
        e4195946(4195946),
        e4195947(4195947),
        e4195948(4195948),
        e4195949(4195949),
        e4195950(4195950),
        e4195951(4195951),
        e4195952(4195952),
        e4195953(4195953),
        e4195956(4195956),
        e4195957(4195957),
        e4195958(4195958),
        e4195959(4195959),
        e4195960(4195960),
        e4195961(4195961),
        e4195962(4195962),
        e4195963(4195963),
        e4195964(4195964),
        e4195965(4195965),
        e4195966(4195966),
        e4195967(4195967),
        e4195968(4195968),
        e4195969(4195969),
        e4195970(4195970),
        e4195971(4195971),
        e4195972(4195972),
        e4195973(4195973),
        e4195976(4195976),
        e4195977(4195977),
        e4195978(4195978),
        e4195979(4195979),
        e4195980(4195980),
        e4195981(4195981),
        e4195982(4195982),
        e4195983(4195983),
        e4195984(4195984),
        e4195985(4195985),
        e4195986(4195986),
        e4195987(4195987),
        e4195988(4195988),
        e4195989(4195989),
        e4195991(4195991),
        e4195992(4195992),
        e4195993(4195993),
        e4195994(4195994),
        e4195995(4195995),
        e4195996(4195996),
        e4195997(4195997),
        e4195998(4195998),
        e4195999(4195999),
        e4196000(4196000),
        e4196001(4196001),
        e4196002(4196002),
        e4196003(4196003),
        e4196004(4196004),
        e4196005(4196005),
        e4196006(4196006),
        e4196007(4196007),
        e4196008(4196008),
        e4196009(4196009),
        e4196010(4196010),
        e4196011(4196011),
        e4196012(4196012),
        e4196013(4196013),
        e4196014(4196014),
        e4196015(4196015),
        e4196016(4196016),
        e4196017(4196017),
        e4196018(4196018),
        e4196019(4196019),
        e4196020(4196020),
        e4196021(4196021),
        e4196023(4196023),
        e4196024(4196024),
        e4196025(4196025),
        e4196026(4196026),
        e4196027(4196027),
        e4196034(4196034),
        e4196035(4196035),
        e4196036(4196036),
        e4196041(4196041),
        e4196042(4196042),
        e4196045(4196045),
        e4196047(4196047),
        e4196048(4196048),
        e4196049(4196049),
        e4196051(4196051),
        e4196052(4196052),
        e4196055(4196055),
        e4196056(4196056),
        e4196060(4196060),
        e4196061(4196061),
        e4196062(4196062),
        e4196063(4196063),
        e4196065(4196065),
        e4196066(4196066),
        e4196067(4196067),
        e4196068(4196068),
        e4196069(4196069),
        e4196070(4196070),
        e4196071(4196071),
        e4196072(4196072),
        e4196073(4196073),
        e4196074(4196074),
        e4196075(4196075),
        e4196076(4196076),
        e4196077(4196077),
        e4196078(4196078),
        e4196079(4196079),
        e4196080(4196080),
        e4196081(4196081),
        e4196082(4196082),
        e4196083(4196083),
        e4196084(4196084),
        e4196085(4196085),
        e4196086(4196086),
        e4196087(4196087),
        e4196088(4196088),
        e4196089(4196089),
        e4196090(4196090),
        e4196091(4196091),
        e4196092(4196092),
        e4196093(4196093),
        e4196094(4196094),
        e4196095(4196095),
        e4196096(4196096),
        e4196097(4196097),
        e4196098(4196098),
        e4196099(4196099),
        e4196100(4196100),
        e4196101(4196101),
        e4196102(4196102),
        e4196103(4196103),
        e4196104(4196104),
        e4196105(4196105),
        e4196106(4196106),
        e4196107(4196107),
        e4196108(4196108),
        e4196109(4196109),
        e4196110(4196110),
        e4196111(4196111),
        e4196112(4196112),
        e4196113(4196113),
        e4196114(4196114),
        e4196115(4196115),
        e4196116(4196116),
        e4196117(4196117),
        e4196118(4196118),
        e4196119(4196119),
        e4196120(4196120),
        e4196121(4196121),
        e4196122(4196122),
        e4196123(4196123),
        e4196124(4196124),
        e4196125(4196125),
        e4196126(4196126),
        e4196127(4196127),
        e4196128(4196128),
        e4196129(4196129),
        e4196130(4196130),
        e4196131(4196131),
        e4196132(4196132),
        e4196133(4196133),
        e4196134(4196134),
        e4196135(4196135),
        e4196136(4196136),
        e4196137(4196137),
        e4196138(4196138),
        e4196139(4196139),
        e4196140(4196140),
        e4196141(4196141),
        e4196142(4196142),
        e4196143(4196143),
        e4196144(4196144),
        e4196145(4196145),
        e4196146(4196146),
        e4196147(4196147),
        e4196149(4196149),
        e4196150(4196150),
        e4196151(4196151),
        e4196152(4196152),
        e4196153(4196153),
        e4196154(4196154),
        e4196155(4196155),
        e4196156(4196156),
        e4196157(4196157),
        e4196158(4196158),
        e4196159(4196159),
        e4196160(4196160),
        e4196161(4196161),
        e4196162(4196162),
        e4196163(4196163),
        e4196164(4196164),
        e4196165(4196165),
        e4196168(4196168),
        e4196169(4196169),
        e4196170(4196170),
        e4196171(4196171),
        e4196172(4196172),
        e4196173(4196173),
        e4196174(4196174),
        e4196175(4196175),
        e4196176(4196176),
        e4196177(4196177),
        e4196178(4196178),
        e4196179(4196179),
        e4196180(4196180),
        e4196181(4196181),
        e4196182(4196182),
        e4196183(4196183),
        e4196184(4196184),
        e4196185(4196185),
        e4196186(4196186),
        e4196187(4196187),
        e4196188(4196188),
        e4196189(4196189),
        e4196190(4196190),
        e4196191(4196191),
        e4196192(4196192),
        e4196193(4196193),
        e4196194(4196194),
        e4196195(4196195),
        e4196196(4196196),
        e4196197(4196197),
        e4196198(4196198),
        e4196199(4196199),
        e4196200(4196200),
        e4196201(4196201),
        e4196202(4196202),
        e4196203(4196203),
        e4196204(4196204),
        e4196205(4196205),
        e4196206(4196206),
        e4196207(4196207),
        e4196208(4196208),
        e4196209(4196209),
        e4196210(4196210),
        e4196211(4196211),
        e4196214(4196214),
        e4196215(4196215),
        e4196216(4196216),
        e4196217(4196217),
        e4196218(4196218),
        e4196219(4196219),
        e4196220(4196220),
        e4196221(4196221),
        e4196222(4196222),
        e4196223(4196223),
        e4196224(4196224),
        e4196225(4196225),
        e4196226(4196226),
        e4196227(4196227),
        e4196228(4196228),
        e4196229(4196229),
        e4196230(4196230),
        e4196231(4196231),
        e4196232(4196232),
        e4196233(4196233),
        e4196234(4196234),
        e4196235(4196235),
        e4196236(4196236),
        e4196237(4196237),
        e4196241(4196241),
        e4196242(4196242),
        e4196243(4196243),
        e4196244(4196244),
        e4196245(4196245),
        e4196246(4196246),
        e4196247(4196247),
        e4196249(4196249),
        e4196250(4196250),
        e4196251(4196251),
        e4196252(4196252),
        e4196253(4196253),
        e4196254(4196254),
        e4196255(4196255),
        e4196259(4196259),
        e4196260(4196260),
        e4196261(4196261),
        e4196262(4196262),
        e4196263(4196263),
        e4196264(4196264),
        e4196265(4196265),
        e4196266(4196266),
        e4196267(4196267),
        e4196268(4196268),
        e4196269(4196269),
        e4196270(4196270),
        e4196271(4196271),
        e4196272(4196272),
        e4196273(4196273),
        e4196274(4196274),
        e4196275(4196275),
        e4196276(4196276),
        e4196277(4196277),
        e4196278(4196278),
        e4196279(4196279),
        e4196280(4196280),
        e4196281(4196281),
        e4196282(4196282),
        e4196283(4196283),
        e4196284(4196284),
        e4196285(4196285),
        e4196286(4196286),
        e4196287(4196287),
        e4196288(4196288),
        e4196289(4196289),
        e4196290(4196290),
        e4196291(4196291),
        e4196292(4196292),
        e4196293(4196293),
        e4196294(4196294),
        e4196295(4196295),
        e4196296(4196296),
        e4196297(4196297),
        e4196298(4196298),
        e4196299(4196299),
        e4196300(4196300),
        e4196301(4196301),
        e4196302(4196302),
        e4196303(4196303),
        e4196304(4196304),
        e4196305(4196305),
        e4196306(4196306),
        e4196307(4196307),
        e4196308(4196308),
        e4196309(4196309),
        e4196310(4196310),
        e4196317(4196317),
        e4196318(4196318),
        e4196319(4196319),
        e4196320(4196320),
        e4196321(4196321),
        e4196322(4196322),
        e4196323(4196323),
        e4196324(4196324),
        e4196325(4196325),
        e4196326(4196326),
        e4196327(4196327),
        e4196328(4196328),
        e4196332(4196332),
        e4196333(4196333),
        e4196334(4196334),
        e4196335(4196335),
        e4196338(4196338),
        e4196342(4196342),
        e4196343(4196343),
        e4196344(4196344),
        e4196345(4196345),
        e4196346(4196346),
        e4196347(4196347),
        e4196348(4196348),
        e4196349(4196349),
        e4196350(4196350),
        e4196354(4196354),
        e4196355(4196355),
        e4196356(4196356),
        e4196357(4196357),
        e4196358(4196358),
        e4196359(4196359),
        e4196360(4196360),
        e4196361(4196361),
        e4196362(4196362),
        e4196363(4196363),
        e4196364(4196364),
        e4196365(4196365),
        e4196366(4196366),
        e4196367(4196367),
        e4196368(4196368),
        e4196369(4196369),
        e4196370(4196370),
        e4196371(4196371),
        e4196372(4196372),
        e4196373(4196373),
        e4196374(4196374),
        e4196375(4196375),
        e4196376(4196376),
        e4196377(4196377),
        e4196378(4196378),
        e4196379(4196379),
        e4196380(4196380),
        e4196382(4196382),
        e4196383(4196383),
        e4196384(4196384),
        e4196385(4196385),
        e4196386(4196386),
        e4196387(4196387),
        e4196388(4196388),
        e4196389(4196389),
        e4196390(4196390),
        e4196391(4196391),
        e4196392(4196392),
        e4196393(4196393),
        e4196394(4196394),
        e4196395(4196395),
        e4196396(4196396),
        f4522530(4522530),
        f4522532(4522532),
        f4522561(4522561),
        f4522588(4522588),
        f4522603(4522603),
        f4525234(4525234),
        f4525239(4525239),
        f4525240(4525240),
        f4525241(4525241),
        f4525247(4525247),
        f4525248(4525248),
        f4525250(4525250),
        f4525251(4525251),
        f4525252(4525252),
        f4525253(4525253),
        f4525254(4525254),
        f4526517(4526517),
        f4526850(4526850),
        f4526851(4526851),
        f4526901(4526901),
        f4526902(4526902),
        f4528207(4528207),
        f4528209(4528209),
        f4528211(4528211),
        f4528216(4528216),
        f4528218(4528218),
        f4528220(4528220),
        f4528223(4528223),
        f4528225(4528225),
        f4528227(4528227),
        f4528268(4528268),
        f4528270(4528270),
        f4528591(4528591),
        f4528596(4528596)
    }

CucsConditionLifecycle ::= TEXTUAL-CONVENTION
    STATUS        current
    DESCRIPTION
        ""
    SYNTAX        BITS {
        flapping(0),
        soakingClear(1)
    }

CucsConditionRemoteInvRslt ::= TEXTUAL-CONVENTION
    STATUS        current
    DESCRIPTION
        ""
    SYNTAX        BITS {
        failure(0),
        unidentifiedFail(1),
        internalError(2),
        timeout(3),
        endPointUnavailable(4),
        endPointFailed(5),
        endPointProtocolError(6),
        swDefect(7),
        fwDefect(8),
        hwDefect(9),
        resourceUnavailable(10),
        resourceCapacityExceeded(11),
        resourceDependency(12),
        capabilityNotImplementedIgnore(13),
        capabilityNotImplementedFailure(14),
        capabilityNotSupported(15),
        capabilityUnavailable(16),
        serviceNotImplementedIgnore(17),
        serviceNotImplementedFail(18),
        serviceNotSupported(19),
        serviceUnavailable(20),
        serviceProtocolError(21),
        fruIdentityIndeterminate(22),
        fruInfoMalformed(23),
        illegalFru(24),
        fruStateIndeterminate(25),
        fruNotReady(26),
        extendTimeout(27),
        taskReset(28),
        fruNotSupported(29),
        intermittentError(30)
    }

CucsConditionRule ::= TEXTUAL-CONVENTION
    STATUS        current
    DESCRIPTION
        ""
    SYNTAX        INTEGER {
        generic(0),
        fabricComputeSlotEpMisplacedInChassisSlot(156),
        fabricComputeSlotEpServerIdentificationProblem(157),
        vnicEtherConfigFailed(169),
        vnicFcConfigFailed(170),
        processorUnitInoperable(174),
        processorUnitThermalNonCritical(175),
        processorUnitThermalThresholdCritical(176),
        processorUnitThermalThresholdNonRecoverable(177),
        processorUnitVoltageThresholdNonCritical(178),
        processorUnitVoltageThresholdCritical(179),
        processorUnitVoltageThresholdNonRecoverable(180),
        storageLocalDiskInoperable(181),
        storageItemCapacityExceeded(182),
        storageItemCapacityWarning(183),
        memoryUnitDegraded(184),
        memoryUnitInoperable(185),
        memoryUnitThermalThresholdNonCritical(186),
        memoryUnitThermalThresholdCritical(187),
        memoryUnitThermalThresholdNonRecoverable(188),
        memoryArrayVoltageThresholdNonCritical(189),
        memoryArrayVoltageThresholdCritical(190),
        memoryArrayVoltageThresholdNonRecoverable(191),
        adaptorUnitUnidentifiableFru(200),
        adaptorUnitMissing(203),
        adaptorUnitAdaptorReachability(206),
        adaptorHostIfLinkDown(207),
        adaptorExtIfLinkDown(209),
        portPioLinkDown(276),
        portPioFailed(277),
        portPioHardwareFailure(278),
        portPioSfpNotPresent(279),
        fabricExternalPcDown(282),
        dcxVcDown(283),
        networkElementInoperable(291),
        mgmtEntityDegraded(293),
        mgmtEntityDown(294),
        dcxNsFailed(304),
        computePhysicalInsufficientlyEquipped(305),
        computePhysicalIdentityUnestablishable(306),
        computeBoardPowerError(310),
        computePhysicalPowerProblem(311),
        computePhysicalThermalProblem(312),
        computePhysicalBiosPostTimeout(313),
        computePhysicalDiscoveryFailed(314),
        computePhysicalAssociationFailed(315),
        computePhysicalInoperable(317),
        computePhysicalUnassignedMissing(318),
        computePhysicalAssignedMissing(319),
        computePhysicalUnidentified(320),
        computePhysicalUnassignedInaccessible(321),
        computePhysicalAssignedInaccessible(322),
        lsServerFailed(324),
        lsServerDiscoveryFailed(326),
        lsServerConfigFailure(327),
        lsServerMaintenanceFailed(329),
        lsServerRemoved(330),
        lsServerInaccessible(331),
        lsServerAssociationFailed(332),
        lsServerUnassociated(334),
        lsServerServerUnfulfilled(337),
        etherSwitchIntfioSatelliteConnectionAbsent(367),
        etherSwitchIntfioSatelliteWiringProblem(368),
        equipmentPsuPowerSupplyProblem(369),
        equipmentFanDegraded(371),
        equipmentFanInoperable(373),
        equipmentPsuInoperable(374),
        equipmentIocardRemoved(376),
        equipmentFanModuleMissing(377),
        equipmentPsuMissing(378),
        equipmentIocardThermalProblem(379),
        equipmentFanModuleThermalThresholdNonCritical(380),
        equipmentPsuThermalThresholdNonCritical(381),
        equipmentFanModuleThermalThresholdCritical(382),
        equipmentPsuThermalThresholdCritical(383),
        equipmentFanModuleThermalThresholdNonRecoverable(384),
        equipmentPsuThermalThresholdNonRecoverable(385),
        equipmentPsuVoltageThresholdNonCritical(387),
        equipmentPsuVoltageThresholdCritical(389),
        equipmentPsuVoltageThresholdNonRecoverable(391),
        equipmentPsuPerfThresholdNonCritical(392),
        equipmentPsuPerfThresholdCritical(393),
        equipmentPsuPerfThresholdNonRecoverable(394),
        equipmentFanPerfThresholdNonCritical(395),
        equipmentFanPerfThresholdCritical(396),
        equipmentFanPerfThresholdNonRecoverable(397),
        equipmentIocardFirmwareUpgrade(398),
        equipmentChassisUnsupportedConnectivity(399),
        equipmentChassisUnacknowledged(400),
        equipmentIocardUnsupportedConnectivity(401),
        equipmentIocardUnacknowledged(402),
        equipmentIocardPeerDisconnected(403),
        equipmentChassisIdentity(404),
        equipmentIocardIdentity(405),
        equipmentFanModuleIdentity(406),
        equipmentPsuIdentity(407),
        equipmentChassisPowerProblem(408),
        equipmentChassisThermalThresholdCritical(409),
        equipmentChassisThermalThresholdNonCritical(410),
        equipmentChassisThermalThresholdNonRecoverable(411),
        computeBoardCmosVoltageThresholdCritical(424),
        computeBoardCmosVoltageThresholdNonRecoverable(425),
        mgmtEntityElectionFailure(428),
        mgmtEntityHaNotReady(429),
        mgmtEntityVersionIncompatible(430),
        equipmentFanMissing(434),
        equipmentIocardAutoUpgradingFirmware(435),
        firmwarePackItemImageMissing(436),
        etherSwitchIntfioSatelliteWiringNumbersUnexpected(440),
        mgmtEntityManagementServicesFailure(451),
        mgmtEntityManagementServicesUnresponsive(452),
        equipmentChassisInoperable(456),
        etherServerIntfioHardwareFailure(458),
        dcxVcMgmtVifDown(459),
        sysdebugMepLogMEpLogLog(460),
        sysdebugMepLogMEpLogVeryLow(461),
        sysdebugMepLogMEpLogFull(462),
        computePoolEmpty(463),
        uuidpoolPoolEmpty(464),
        ippoolPoolEmpty(465),
        macpoolPoolEmpty(466),
        firmwareUpdatableImageUnusable(470),
        firmwareBootUnitCantBoot(471),
        fcpoolInitiatorsEmpty(476),
        equipmentIocardInaccessible(478),
        dcxVifLinkState(479),
        equipmentFanModuleDegraded(480),
        equipmentIocardPostFailure(481),
        equipmentFanPerfThresholdLowerNonRecoverable(484),
        memoryUnitIdentityUnestablishable(502),
        computePhysicalPostFailure(517),
        equipmentPsuOffline(528),
        sysdebugMepLogTransferError(530),
        storageRaidBatteryInoperable(560),
        computeRtcBatteryInoperable(561),
        memoryBufferUnitThermalThresholdNonCritical(577),
        memoryBufferUnitThermalThresholdCritical(578),
        memoryBufferUnitThermalThresholdNonRecoverable(579),
        computeIohubThermalNonCritical(582),
        computeIohubThermalThresholdCritical(583),
        computeIohubThermalThresholdNonRecoverable(584),
        equipmentChassisIdentityUnestablishable(587),
        licenseInstanceGracePeriodWarning1(591),
        licenseInstanceGracePeriodWarning2(592),
        licenseInstanceGracePeriodWarning3(593),
        licenseInstanceGracePeriodWarning4(594),
        licenseInstanceGracePeriodWarning5(595),
        licenseInstanceGracePeriodWarning6(596),
        licenseInstanceGracePeriodWarning7(597),
        licenseFileBadLicenseFile(598),
        licenseFileFileNotDeleted(599),
        fabricLanPinGroupEmpty(621),
        fabricSanPinGroupEmpty(622),
        adaptorExtEthIfMisConnect(625),
        swVlanPortNsResourceStatus(635),
        fabricVlanPrimaryVlanMissingIsolated(646),
        mgmtIfMisConnect(654),
        adaptorHostEthIfMisConnect(656),
        equipmentFexPostFailure(669),
        equipmentFexIdentity(670),
        powerBudgetPowerBudgetCmcProblem(688),
        lsComputeBindingAssignmentRequirementsNotMet(689),
        powerBudgetPowerBudgetBmcProblem(690),
        powerBudgetPowerBudgetDiscFail(693),
        powerGroupPowerGroupInsufficientBudget(695),
        powerGroupPowerGroupBudgetIncorrect(696),
        adaptorHostEthIfMissing(708),
        portPioInvalidSfp(710),
        mgmtIfMissing(714),
        fabricEthLanPcEpDown(727),
        fabricFcSanPcEpDown(728),
        equipmentIocardThermalThresholdNonCritical(729),
        equipmentIocardThermalThresholdCritical(730),
        equipmentIocardThermalThresholdNonRecoverable(731),
        equipmentChassisSeepromInoperable(733),
        fabricFcSanPcEpIncompatibleSpeed(734),
        fabricFcSanPcIncompatibleSpeed(735),
        extmgmtIfMgmtifdown(736),
        powerChassisMemberPowerGroupCapInsufficient(740),
        powerChassisMemberChassisFirmwareProblem(741),
        powerChassisMemberChassisPsuInsufficient(742),
        powerChassisMemberChassisPsuRedundanceFailure(743),
        powerBudgetPowerCapReachedCommit(744),
        sysdebugAutoCoreFileExportTargetAutoCoreTransferFailure(747),
        fabricMonSpanConfigFail(757),
        powerBudgetChassisPsuInsufficient(764),
        powerBudgetTstateTransition(765),
        powerPolicyPowerPolicyApplicationFail(766),
        mgmtIfNew(772),
        adaptorExtEthIfMissing(775),
        storageLocalDiskSlotEpUnusable(776),
        fabricEthEstcPcEpDown(777),
        equipmentFexIdentityUnestablishable(778),
        mgmtEntityDevice1SeepromError(791),
        mgmtEntityDevice2SeepromError(792),
        mgmtEntityDevice3SeepromError(793),
        equipmentFanModuleInoperable(794),
        fsmFePresence(16405),
        fsmFeConn(16406),
        fsmRemoveChassis(16407),
        fsmSetLocatorLed(16408),
        fsmExtMgmtIfConfig(16518),
        fsmIdentify(16519),
        fsmPsuPolicyConfig(16533),
        fsmResetFcPersBinding(16534),
        fsmDiag(16535),
        fsmSwitchMode(16539),
        fsmUpdateSvcEp(16576),
        fsmRestartWebSvc(16577),
        fsmUpdateEp(16579),
        fsmUpdateRealm(16580),
        fsmUpdateUserEp(16581),
        fsmSingle(16600),
        fsmGlobal(16601),
        fsmExport(16604),
        fsmLogControlPersist(16606),
        fsmCreate(16641),
        fsmDownload(16650),
        fsmDelete(16651),
        fsmUpdateSwitch(16653),
        fsmUpdateiom(16654),
        fsmActivateiom(16655),
        fsmUpdatebmc(16656),
        fsmActivatebmc(16657),
        fsmConfigCallhome(16670),
        fsmSwMgmtOobIfConfig(16673),
        fsmSwMgmtInbandIfConfig(16674),
        fsmVirtualIfConfig(16679),
        fsmEnableVip(16680),
        fsmDisableVip(16681),
        fsmEnableha(16682),
        fsmBackup(16683),
        fsmImport(16684),
        fsmConfigGlobalQos(16745),
        fsmRemove(16750),
        fsmResetCmc(16803),
        fsmUpdateucsmanager(16815),
        fsmSysConfig(16823),
        fsmPathReset(16852),
        fsmCircuitReset(16857),
        fsmConfig(16879),
        fsmCertInstall(16880),
        fsmRemoveProvider(16881),
        fsmUpdater(16904),
        fsmDiscover(16920),
        fsmAssociate(16921),
        fsmDisassociate(16922),
        fsmDecommission(16924),
        fsmSoftShutdown(16925),
        fsmHardShutdown(16926),
        fsmTurnup(16927),
        fsmPowercycle(16928),
        fsmHardreset(16929),
        fsmSoftreset(16930),
        fsmSwConnUpd(16931),
        fsmBiosRecovery(16932),
        fsmCmosReset(16934),
        fsmResetBmc(16935),
        fsmUpdateExtUsers(16938),
        fsmUpdateAdaptor(16939),
        fsmActivateAdaptor(16940),
        fsmConfigSol(16941),
        fsmUnconfigSol(16942),
        fsmSetFeLocatorLed(16943),
        fsmPowerCap(16950),
        fsmUpdateBoardController(16964),
        fsmDeployCatalogue(16965),
        fsmInstall(16991),
        fsmClear(16992),
        fsmUpdateFlexlm(16993),
        fsmRemoveFex(17007),
        fsmInitiate(17012),
        fsmDeleteTechSupFile(17013),
        fsmActivateCatalog(17017),
        fsmActivateMgmtExt(17018),
        fsmDeploy(17050),
        fsmResetIom(17052),
        fsmConfigure(17060),
        fsmMuxOffline(17061),
        fsmInCompatSfpPresence(17089),
        fsmDiagnosticInterrupt(17116),
        fsmDynamicReallocation(17134),
        fsmResetKvm(17163),
        fsmOnline(17169),
        fsmOffline(17170),
        tcaProcessorRuntimeLoad(33142),
        tcaProcessorRuntimeLoadMin(33144),
        tcaProcessorRuntimeLoadMax(33145),
        tcaProcessorRuntimeLoadAvg(33146),
        tcaFcStatsBytesRxDelta(33167),
        tcaFcStatsBytesRxDeltaMin(33168),
        tcaFcStatsBytesRxDeltaMax(33169),
        tcaFcStatsBytesRxDeltaAvg(33170),
        tcaFcStatsPacketsRxDelta(33177),
        tcaFcStatsPacketsRxDeltaMin(33178),
        tcaFcStatsPacketsRxDeltaMax(33179),
        tcaFcStatsPacketsRxDeltaAvg(33180),
        tcaFcStatsBytesTxDelta(33187),
        tcaFcStatsBytesTxDeltaMin(33188),
        tcaFcStatsBytesTxDeltaMax(33189),
        tcaFcStatsBytesTxDeltaAvg(33190),
        tcaFcStatsPacketsTxDelta(33197),
        tcaFcStatsPacketsTxDeltaMin(33198),
        tcaFcStatsPacketsTxDeltaMax(33199),
        tcaFcStatsPacketsTxDeltaAvg(33200),
        tcaFcErrStatsCrcRxDelta(33211),
        tcaFcErrStatsCrcRxDeltaMin(33212),
        tcaFcErrStatsCrcRxDeltaMax(33213),
        tcaFcErrStatsCrcRxDeltaAvg(33214),
        tcaFcErrStatsDiscardRxDelta(33221),
        tcaFcErrStatsDiscardRxDeltaMin(33222),
        tcaFcErrStatsDiscardRxDeltaMax(33223),
        tcaFcErrStatsDiscardRxDeltaAvg(33224),
        tcaFcErrStatsTooLongRxDelta(33231),
        tcaFcErrStatsTooLongRxDeltaMin(33232),
        tcaFcErrStatsTooLongRxDeltaMax(33233),
        tcaFcErrStatsTooLongRxDeltaAvg(33234),
        tcaFcErrStatsTooShortRxDelta(33241),
        tcaFcErrStatsTooShortRxDeltaMin(33242),
        tcaFcErrStatsTooShortRxDeltaMax(33243),
        tcaFcErrStatsTooShortRxDeltaAvg(33244),
        tcaFcErrStatsRxDelta(33251),
        tcaFcErrStatsRxDeltaMin(33252),
        tcaFcErrStatsRxDeltaMax(33253),
        tcaFcErrStatsRxDeltaAvg(33254),
        tcaFcErrStatsDiscardTxDelta(33261),
        tcaFcErrStatsDiscardTxDeltaMin(33262),
        tcaFcErrStatsDiscardTxDeltaMax(33263),
        tcaFcErrStatsDiscardTxDeltaAvg(33264),
        tcaFcErrStatsTxDelta(33271),
        tcaFcErrStatsTxDeltaMin(33272),
        tcaFcErrStatsTxDeltaMax(33273),
        tcaFcErrStatsTxDeltaAvg(33274),
        tcaFcErrStatsLinkFailuresDelta(33281),
        tcaFcErrStatsLinkFailuresDeltaMin(33282),
        tcaFcErrStatsLinkFailuresDeltaMax(33283),
        tcaFcErrStatsLinkFailuresDeltaAvg(33284),
        tcaFcErrStatsSyncLossesDelta(33291),
        tcaFcErrStatsSyncLossesDeltaMin(33292),
        tcaFcErrStatsSyncLossesDeltaMax(33293),
        tcaFcErrStatsSyncLossesDeltaAvg(33294),
        tcaFcErrStatsSignalLossesDelta(33301),
        tcaFcErrStatsSignalLossesDeltaMin(33302),
        tcaFcErrStatsSignalLossesDeltaMax(33303),
        tcaFcErrStatsSignalLossesDeltaAvg(33304),
        tcaMemoryRuntimeTotal(33483),
        tcaMemoryRuntimeTotalMin(33485),
        tcaMemoryRuntimeTotalMax(33486),
        tcaMemoryRuntimeTotalAvg(33487),
        tcaMemoryRuntimeAvailable(33491),
        tcaMemoryRuntimeAvailableMin(33493),
        tcaMemoryRuntimeAvailableMax(33494),
        tcaMemoryRuntimeAvailableAvg(33495),
        tcaMemoryRuntimeCached(33499),
        tcaMemoryRuntimeCachedMin(33501),
        tcaMemoryRuntimeCachedMax(33502),
        tcaMemoryRuntimeCachedAvg(33503),
        tcaAdaptorEthPortStatsTotalPacketsDelta(33720),
        tcaAdaptorEthPortStatsTotalPacketsDeltaMin(33721),
        tcaAdaptorEthPortStatsTotalPacketsDeltaMax(33722),
        tcaAdaptorEthPortStatsTotalPacketsDeltaAvg(33723),
        tcaAdaptorEthPortStatsGoodPacketsDelta(33730),
        tcaAdaptorEthPortStatsGoodPacketsDeltaMin(33731),
        tcaAdaptorEthPortStatsGoodPacketsDeltaMax(33732),
        tcaAdaptorEthPortStatsGoodPacketsDeltaAvg(33733),
        tcaAdaptorEthPortStatsVlanPacketsDelta(33740),
        tcaAdaptorEthPortStatsVlanPacketsDeltaMin(33741),
        tcaAdaptorEthPortStatsVlanPacketsDeltaMax(33742),
        tcaAdaptorEthPortStatsVlanPacketsDeltaAvg(33743),
        tcaAdaptorEthPortStatsPausePacketsDelta(33750),
        tcaAdaptorEthPortStatsPausePacketsDeltaMin(33751),
        tcaAdaptorEthPortStatsPausePacketsDeltaMax(33752),
        tcaAdaptorEthPortStatsPausePacketsDeltaAvg(33753),
        tcaAdaptorEthPortStatsPerPriorityPausePacketsDelta(33760),
        tcaAdaptorEthPortStatsPerPriorityPausePacketsDeltaMin(33761),
        tcaAdaptorEthPortStatsPerPriorityPausePacketsDeltaMax(33762),
        tcaAdaptorEthPortStatsPerPriorityPausePacketsDeltaAvg(33763),
        tcaAdaptorEthPortStatsPppPacketsDelta(33770),
        tcaAdaptorEthPortStatsPppPacketsDeltaMin(33771),
        tcaAdaptorEthPortStatsPppPacketsDeltaMax(33772),
        tcaAdaptorEthPortStatsPppPacketsDeltaAvg(33773),
        tcaAdaptorEthPortBySizeSmallStatsLessThan64Delta(33810),
        tcaAdaptorEthPortBySizeSmallStatsLessThan64DeltaMin(33811),
        tcaAdaptorEthPortBySizeSmallStatsLessThan64DeltaMax(33812),
        tcaAdaptorEthPortBySizeSmallStatsLessThan64DeltaAvg(33813),
        tcaAdaptorEthPortBySizeSmallStatsEquals64Delta(33820),
        tcaAdaptorEthPortBySizeSmallStatsEquals64DeltaMin(33821),
        tcaAdaptorEthPortBySizeSmallStatsEquals64DeltaMax(33822),
        tcaAdaptorEthPortBySizeSmallStatsEquals64DeltaAvg(33823),
        tcaAdaptorEthPortBySizeSmallStatsLessThan128Delta(33830),
        tcaAdaptorEthPortBySizeSmallStatsLessThan128DeltaMin(33831),
        tcaAdaptorEthPortBySizeSmallStatsLessThan128DeltaMax(33832),
        tcaAdaptorEthPortBySizeSmallStatsLessThan128DeltaAvg(33833),
        tcaAdaptorEthPortBySizeSmallStatsLessThan256Delta(33840),
        tcaAdaptorEthPortBySizeSmallStatsLessThan256DeltaMin(33841),
        tcaAdaptorEthPortBySizeSmallStatsLessThan256DeltaMax(33842),
        tcaAdaptorEthPortBySizeSmallStatsLessThan256DeltaAvg(33843),
        tcaAdaptorEthPortBySizeSmallStatsLessThan512Delta(33850),
        tcaAdaptorEthPortBySizeSmallStatsLessThan512DeltaMin(33851),
        tcaAdaptorEthPortBySizeSmallStatsLessThan512DeltaMax(33852),
        tcaAdaptorEthPortBySizeSmallStatsLessThan512DeltaAvg(33853),
        tcaAdaptorEthPortBySizeSmallStatsLessThan1024Delta(33860),
        tcaAdaptorEthPortBySizeSmallStatsLessThan1024DeltaMin(33861),
        tcaAdaptorEthPortBySizeSmallStatsLessThan1024DeltaMax(33862),
        tcaAdaptorEthPortBySizeSmallStatsLessThan1024DeltaAvg(33863),
        tcaAdaptorEthPortBySizeLargeStatsLessThanOrEqualTo1518Delta(33875),
        tcaAdaptorEthPortBySizeLargeStatsLessThanOrEqualTo1518DeltaMin(33876),
        tcaAdaptorEthPortBySizeLargeStatsLessThanOrEqualTo1518DeltaMax(33877),
        tcaAdaptorEthPortBySizeLargeStatsLessThanOrEqualTo1518DeltaAvg(33878),
        tcaAdaptorEthPortBySizeLargeStatsLessThan2048Delta(33885),
        tcaAdaptorEthPortBySizeLargeStatsLessThan2048DeltaMin(33886),
        tcaAdaptorEthPortBySizeLargeStatsLessThan2048DeltaMax(33887),
        tcaAdaptorEthPortBySizeLargeStatsLessThan2048DeltaAvg(33888),
        tcaAdaptorEthPortBySizeLargeStatsLessThan4096Delta(33895),
        tcaAdaptorEthPortBySizeLargeStatsLessThan4096DeltaMin(33896),
        tcaAdaptorEthPortBySizeLargeStatsLessThan4096DeltaMax(33897),
        tcaAdaptorEthPortBySizeLargeStatsLessThan4096DeltaAvg(33898),
        tcaAdaptorEthPortBySizeLargeStatsLessThan8192Delta(33905),
        tcaAdaptorEthPortBySizeLargeStatsLessThan8192DeltaMin(33906),
        tcaAdaptorEthPortBySizeLargeStatsLessThan8192DeltaMax(33907),
        tcaAdaptorEthPortBySizeLargeStatsLessThan8192DeltaAvg(33908),
        tcaAdaptorEthPortBySizeLargeStatsLessThan9216Delta(33915),
        tcaAdaptorEthPortBySizeLargeStatsLessThan9216DeltaMin(33916),
        tcaAdaptorEthPortBySizeLargeStatsLessThan9216DeltaMax(33917),
        tcaAdaptorEthPortBySizeLargeStatsLessThan9216DeltaAvg(33918),
        tcaAdaptorEthPortBySizeLargeStatsGreaterThanOrEqualTo9216Delta(33925),
        tcaAdaptorEthPrtBySizeLargeStatsGreaterThanOrEqualTo9216DeltaMin(33926),
        tcaAdaptorEthPrtBySizeLargeStatsGreaterThanOrEqualTo9216DeltaMax(33927),
        tcaAdaptorEthPrtBySizeLargeStatsGreaterThanOrEqualTo9216DeltaAvg(33928),
        tcaAdaptorEthPortOutsizedStatsOversizedPacketsDelta(33940),
        tcaAdaptorEthPortOutsizedStatsOversizedPacketsDeltaMin(33941),
        tcaAdaptorEthPortOutsizedStatsOversizedPacketsDeltaMax(33942),
        tcaAdaptorEthPortOutsizedStatsOversizedPacketsDeltaAvg(33943),
        tcaAdaptorEthPortOutsizedStatsOversizedGoodCrcPacketsDelta(33950),
        tcaAdaptorEthPortOutsizedStatsOversizedGoodCrcPacketsDeltaMin(33951),
        tcaAdaptorEthPortOutsizedStatsOversizedGoodCrcPacketsDeltaMax(33952),
        tcaAdaptorEthPortOutsizedStatsOversizedGoodCrcPacketsDeltaAvg(33953),
        tcaAdaptorEthPortOutsizedStatsOversizedBadCrcPacketsDelta(33960),
        tcaAdaptorEthPortOutsizedStatsOversizedBadCrcPacketsDeltaMin(33961),
        tcaAdaptorEthPortOutsizedStatsOversizedBadCrcPacketsDeltaMax(33962),
        tcaAdaptorEthPortOutsizedStatsOversizedBadCrcPacketsDeltaAvg(33963),
        tcaAdaptorEthPortOutsizedStatsUndersizedGoodCrcPacketsDelta(33970),
        tcaAdaptorEthPortOutsizedStatsUndersizedGoodCrcPacketsDeltaMin(33971),
        tcaAdaptorEthPortOutsizedStatsUndersizedGoodCrcPacketsDeltaMax(33972),
        tcaAdaptorEthPortOutsizedStatsUndersizedGoodCrcPacketsDeltaAvg(33973),
        tcaAdaptorEthPortOutsizedStatsUndersizedBadCrcPacketsDelta(33980),
        tcaAdaptorEthPortOutsizedStatsUndersizedBadCrcPacketsDeltaMin(33981),
        tcaAdaptorEthPortOutsizedStatsUndersizedBadCrcPacketsDeltaMax(33982),
        tcaAdaptorEthPortOutsizedStatsUndersizedBadCrcPacketsDeltaAvg(33983),
        tcaAdaptorEthPortMcastStatsUnicastPacketsDelta(33995),
        tcaAdaptorEthPortMcastStatsUnicastPacketsDeltaMin(33996),
        tcaAdaptorEthPortMcastStatsUnicastPacketsDeltaMax(33997),
        tcaAdaptorEthPortMcastStatsUnicastPacketsDeltaAvg(33998),
        tcaAdaptorEthPortMcastStatsMulticastPacketsDelta(34005),
        tcaAdaptorEthPortMcastStatsMulticastPacketsDeltaMin(34006),
        tcaAdaptorEthPortMcastStatsMulticastPacketsDeltaMax(34007),
        tcaAdaptorEthPortMcastStatsMulticastPacketsDeltaAvg(34008),
        tcaAdaptorEthPortMcastStatsBroadcastPacketsDelta(34015),
        tcaAdaptorEthPortMcastStatsBroadcastPacketsDeltaMin(34016),
        tcaAdaptorEthPortMcastStatsBroadcastPacketsDeltaMax(34017),
        tcaAdaptorEthPortMcastStatsBroadcastPacketsDeltaAvg(34018),
        tcaAdaptorEthPortErrStatsMacDiscardedPacketsDelta(34030),
        tcaAdaptorEthPortErrStatsMacDiscardedPacketsDeltaMin(34031),
        tcaAdaptorEthPortErrStatsMacDiscardedPacketsDeltaMax(34032),
        tcaAdaptorEthPortErrStatsMacDiscardedPacketsDeltaAvg(34033),
        tcaAdaptorEthPortErrStatsBadCrcPacketsDelta(34040),
        tcaAdaptorEthPortErrStatsBadCrcPacketsDeltaMin(34041),
        tcaAdaptorEthPortErrStatsBadCrcPacketsDeltaMax(34042),
        tcaAdaptorEthPortErrStatsBadCrcPacketsDeltaAvg(34043),
        tcaAdaptorEthPortErrStatsBadLengthPacketsDelta(34050),
        tcaAdaptorEthPortErrStatsBadLengthPacketsDeltaMin(34051),
        tcaAdaptorEthPortErrStatsBadLengthPacketsDeltaMax(34052),
        tcaAdaptorEthPortErrStatsBadLengthPacketsDeltaAvg(34053),
        tcaAdaptorFcPortStatsRxFramesDelta(34064),
        tcaAdaptorFcPortStatsRxFramesDeltaMin(34065),
        tcaAdaptorFcPortStatsRxFramesDeltaMax(34066),
        tcaAdaptorFcPortStatsRxFramesDeltaAvg(34067),
        tcaAdaptorFcPortStatsTxFramesDelta(34074),
        tcaAdaptorFcPortStatsTxFramesDeltaMin(34075),
        tcaAdaptorFcPortStatsTxFramesDeltaMax(34076),
        tcaAdaptorFcPortStatsTxFramesDeltaAvg(34077),
        tcaAdaptorFcPortStatsRxBadFramesDelta(34084),
        tcaAdaptorFcPortStatsRxBadFramesDeltaMin(34085),
        tcaAdaptorFcPortStatsRxBadFramesDeltaMax(34086),
        tcaAdaptorFcPortStatsRxBadFramesDeltaAvg(34087),
        tcaAdaptorFcPortStatsTxBadFramesDelta(34094),
        tcaAdaptorFcPortStatsTxBadFramesDeltaMin(34095),
        tcaAdaptorFcPortStatsTxBadFramesDeltaMax(34096),
        tcaAdaptorFcPortStatsTxBadFramesDeltaAvg(34097),
        tcaAdaptorVnicStatsPacketsTxDelta(34108),
        tcaAdaptorVnicStatsPacketsTxDeltaMin(34109),
        tcaAdaptorVnicStatsPacketsTxDeltaMax(34110),
        tcaAdaptorVnicStatsPacketsTxDeltaAvg(34111),
        tcaAdaptorVnicStatsPacketsRxDelta(34118),
        tcaAdaptorVnicStatsPacketsRxDeltaMin(34119),
        tcaAdaptorVnicStatsPacketsRxDeltaMax(34120),
        tcaAdaptorVnicStatsPacketsRxDeltaAvg(34121),
        tcaAdaptorVnicStatsBytesTxDelta(34128),
        tcaAdaptorVnicStatsBytesTxDeltaMin(34129),
        tcaAdaptorVnicStatsBytesTxDeltaMax(34130),
        tcaAdaptorVnicStatsBytesTxDeltaAvg(34131),
        tcaAdaptorVnicStatsBytesRxDelta(34138),
        tcaAdaptorVnicStatsBytesRxDeltaMin(34139),
        tcaAdaptorVnicStatsBytesRxDeltaMax(34140),
        tcaAdaptorVnicStatsBytesRxDeltaAvg(34141),
        tcaAdaptorVnicStatsErrorsTxDelta(34148),
        tcaAdaptorVnicStatsErrorsTxDeltaMin(34149),
        tcaAdaptorVnicStatsErrorsTxDeltaMax(34150),
        tcaAdaptorVnicStatsErrorsTxDeltaAvg(34151),
        tcaAdaptorVnicStatsErrorsRxDelta(34158),
        tcaAdaptorVnicStatsErrorsRxDeltaMin(34159),
        tcaAdaptorVnicStatsErrorsRxDeltaMax(34160),
        tcaAdaptorVnicStatsErrorsRxDeltaAvg(34161),
        tcaAdaptorVnicStatsDroppedTxDelta(34168),
        tcaAdaptorVnicStatsDroppedTxDeltaMin(34169),
        tcaAdaptorVnicStatsDroppedTxDeltaMax(34170),
        tcaAdaptorVnicStatsDroppedTxDeltaAvg(34171),
        tcaAdaptorVnicStatsDroppedRxDelta(34178),
        tcaAdaptorVnicStatsDroppedRxDeltaMin(34179),
        tcaAdaptorVnicStatsDroppedRxDeltaMax(34180),
        tcaAdaptorVnicStatsDroppedRxDeltaAvg(34181),
        tcaAdaptorFcIffc4StatsInputRequestsDelta(34192),
        tcaAdaptorFcIffc4StatsInputRequestsDeltaMin(34193),
        tcaAdaptorFcIffc4StatsInputRequestsDeltaMax(34194),
        tcaAdaptorFcIffc4StatsInputRequestsDeltaAvg(34195),
        tcaAdaptorFcIffc4StatsOutputRequestsDelta(34202),
        tcaAdaptorFcIffc4StatsOutputRequestsDeltaMin(34203),
        tcaAdaptorFcIffc4StatsOutputRequestsDeltaMax(34204),
        tcaAdaptorFcIffc4StatsOutputRequestsDeltaAvg(34205),
        tcaAdaptorFcIffc4StatsControlRequestsDelta(34212),
        tcaAdaptorFcIffc4StatsControlRequestsDeltaMin(34213),
        tcaAdaptorFcIffc4StatsControlRequestsDeltaMax(34214),
        tcaAdaptorFcIffc4StatsControlRequestsDeltaAvg(34215),
        tcaAdaptorFcIffc4StatsInputMegabytesDelta(34222),
        tcaAdaptorFcIffc4StatsInputMegabytesDeltaMin(34223),
        tcaAdaptorFcIffc4StatsInputMegabytesDeltaMax(34224),
        tcaAdaptorFcIffc4StatsInputMegabytesDeltaAvg(34225),
        tcaAdaptorFcIffc4StatsOutputMegabytesDelta(34232),
        tcaAdaptorFcIffc4StatsOutputMegabytesDeltaMin(34233),
        tcaAdaptorFcIffc4StatsOutputMegabytesDeltaMax(34234),
        tcaAdaptorFcIffc4StatsOutputMegabytesDeltaAvg(34235),
        tcaAdaptorMenloBaseErrorStatsCorrectableErrorsDelta(34246),
        tcaAdaptorMenloBaseErrorStatsCorrectableErrorsDeltaMin(34247),
        tcaAdaptorMenloBaseErrorStatsCorrectableErrorsDeltaMax(34248),
        tcaAdaptorMenloBaseErrorStatsCorrectableErrorsDeltaAvg(34249),
        tcaAdaptorMenloBaseErrorStatsUncorrectableErrorsDelta(34256),
        tcaAdaptorMenloBaseErrorStatsUncorrectableErrorsDeltaMin(34257),
        tcaAdaptorMenloBaseErrorStatsUncorrectableErrorsDeltaMax(34258),
        tcaAdaptorMenloBaseErrorStatsUncorrectableErrorsDeltaAvg(34259),
        tcaAdaptorMenloMcpuStatsDropAclDelta(34271),
        tcaAdaptorMenloMcpuStatsDropAclDeltaMin(34272),
        tcaAdaptorMenloMcpuStatsDropAclDeltaMax(34273),
        tcaAdaptorMenloMcpuStatsDropAclDeltaAvg(34274),
        tcaAdaptorMenloMcpuStatsDropOverrunDelta(34281),
        tcaAdaptorMenloMcpuStatsDropOverrunDeltaMin(34282),
        tcaAdaptorMenloMcpuStatsDropOverrunDeltaMax(34283),
        tcaAdaptorMenloMcpuStatsDropOverrunDeltaAvg(34284),
        tcaAdaptorMenloMcpuStatsDropRuntDelta(34291),
        tcaAdaptorMenloMcpuStatsDropRuntDeltaMin(34292),
        tcaAdaptorMenloMcpuStatsDropRuntDeltaMax(34293),
        tcaAdaptorMenloMcpuStatsDropRuntDeltaAvg(34294),
        tcaAdaptorMenloMcpuStatsTruncateOverrunDelta(34301),
        tcaAdaptorMenloMcpuStatsTruncateOverrunDeltaMin(34302),
        tcaAdaptorMenloMcpuStatsTruncateOverrunDeltaMax(34303),
        tcaAdaptorMenloMcpuStatsTruncateOverrunDeltaAvg(34304),
        tcaAdaptorMenloMcpuErrorStatsCorrectableErrorsDelta(34316),
        tcaAdaptorMenloMcpuErrorStatsCorrectableErrorsDeltaMin(34317),
        tcaAdaptorMenloMcpuErrorStatsCorrectableErrorsDeltaMax(34318),
        tcaAdaptorMenloMcpuErrorStatsCorrectableErrorsDeltaAvg(34319),
        tcaAdaptorMenloMcpuErrorStatsPopErrorsDelta(34326),
        tcaAdaptorMenloMcpuErrorStatsPopErrorsDeltaMin(34327),
        tcaAdaptorMenloMcpuErrorStatsPopErrorsDeltaMax(34328),
        tcaAdaptorMenloMcpuErrorStatsPopErrorsDeltaAvg(34329),
        tcaAdaptorMenloMcpuErrorStatsPushErrorsDelta(34336),
        tcaAdaptorMenloMcpuErrorStatsPushErrorsDeltaMin(34337),
        tcaAdaptorMenloMcpuErrorStatsPushErrorsDeltaMax(34338),
        tcaAdaptorMenloMcpuErrorStatsPushErrorsDeltaAvg(34339),
        tcaAdaptorMenloMcpuErrorStatsUncorrectableErrorsDelta(34346),
        tcaAdaptorMenloMcpuErrorStatsUncorrectableErrorsDeltaMin(34347),
        tcaAdaptorMenloMcpuErrorStatsUncorrectableErrorsDeltaMax(34348),
        tcaAdaptorMenloMcpuErrorStatsUncorrectableErrorsDeltaAvg(34349),
        tcaAdaptorMenloEthStatsDropOverrunDelta(34361),
        tcaAdaptorMenloEthStatsDropOverrunDeltaMin(34362),
        tcaAdaptorMenloEthStatsDropOverrunDeltaMax(34363),
        tcaAdaptorMenloEthStatsDropOverrunDeltaAvg(34364),
        tcaAdaptorMenloEthStatsDropRuntDelta(34371),
        tcaAdaptorMenloEthStatsDropRuntDeltaMin(34372),
        tcaAdaptorMenloEthStatsDropRuntDeltaMax(34373),
        tcaAdaptorMenloEthStatsDropRuntDeltaAvg(34374),
        tcaAdaptorMenloEthStatsTruncateOverrunDelta(34381),
        tcaAdaptorMenloEthStatsTruncateOverrunDeltaMin(34382),
        tcaAdaptorMenloEthStatsTruncateOverrunDeltaMax(34383),
        tcaAdaptorMenloEthStatsTruncateOverrunDeltaAvg(34384),
        tcaAdaptorMenloEthErrorStatsCorrectableErrorsDelta(34396),
        tcaAdaptorMenloEthErrorStatsCorrectableErrorsDeltaMin(34397),
        tcaAdaptorMenloEthErrorStatsCorrectableErrorsDeltaMax(34398),
        tcaAdaptorMenloEthErrorStatsCorrectableErrorsDeltaAvg(34399),
        tcaAdaptorMenloEthErrorStatsDropAclDelta(34406),
        tcaAdaptorMenloEthErrorStatsDropAclDeltaMin(34407),
        tcaAdaptorMenloEthErrorStatsDropAclDeltaMax(34408),
        tcaAdaptorMenloEthErrorStatsDropAclDeltaAvg(34409),
        tcaAdaptorMenloEthErrorStatsPopErrorsDelta(34416),
        tcaAdaptorMenloEthErrorStatsPopErrorsDeltaMin(34417),
        tcaAdaptorMenloEthErrorStatsPopErrorsDeltaMax(34418),
        tcaAdaptorMenloEthErrorStatsPopErrorsDeltaAvg(34419),
        tcaAdaptorMenloEthErrorStatsPushErrorsDelta(34426),
        tcaAdaptorMenloEthErrorStatsPushErrorsDeltaMin(34427),
        tcaAdaptorMenloEthErrorStatsPushErrorsDeltaMax(34428),
        tcaAdaptorMenloEthErrorStatsPushErrorsDeltaAvg(34429),
        tcaAdaptorMenloEthErrorStatsUncorrectableErrorsDelta(34436),
        tcaAdaptorMenloEthErrorStatsUncorrectableErrorsDeltaMin(34437),
        tcaAdaptorMenloEthErrorStatsUncorrectableErrorsDeltaMax(34438),
        tcaAdaptorMenloEthErrorStatsUncorrectableErrorsDeltaAvg(34439),
        tcaAdaptorMenloFcStatsDropAclDelta(34451),
        tcaAdaptorMenloFcStatsDropAclDeltaMin(34452),
        tcaAdaptorMenloFcStatsDropAclDeltaMax(34453),
        tcaAdaptorMenloFcStatsDropAclDeltaAvg(34454),
        tcaAdaptorMenloFcStatsDropOverrunDelta(34461),
        tcaAdaptorMenloFcStatsDropOverrunDeltaMin(34462),
        tcaAdaptorMenloFcStatsDropOverrunDeltaMax(34463),
        tcaAdaptorMenloFcStatsDropOverrunDeltaAvg(34464),
        tcaAdaptorMenloFcStatsDropRuntDelta(34471),
        tcaAdaptorMenloFcStatsDropRuntDeltaMin(34472),
        tcaAdaptorMenloFcStatsDropRuntDeltaMax(34473),
        tcaAdaptorMenloFcStatsDropRuntDeltaAvg(34474),
        tcaAdaptorMenloFcStatsTruncateOverrunDelta(34481),
        tcaAdaptorMenloFcStatsTruncateOverrunDeltaMin(34482),
        tcaAdaptorMenloFcStatsTruncateOverrunDeltaMax(34483),
        tcaAdaptorMenloFcStatsTruncateOverrunDeltaAvg(34484),
        tcaAdaptorMenloFcErrorStatsCorrectableErrorsDelta(34496),
        tcaAdaptorMenloFcErrorStatsCorrectableErrorsDeltaMin(34497),
        tcaAdaptorMenloFcErrorStatsCorrectableErrorsDeltaMax(34498),
        tcaAdaptorMenloFcErrorStatsCorrectableErrorsDeltaAvg(34499),
        tcaAdaptorMenloFcErrorStatsPopErrorsDelta(34506),
        tcaAdaptorMenloFcErrorStatsPopErrorsDeltaMin(34507),
        tcaAdaptorMenloFcErrorStatsPopErrorsDeltaMax(34508),
        tcaAdaptorMenloFcErrorStatsPopErrorsDeltaAvg(34509),
        tcaAdaptorMenloFcErrorStatsPushErrorsDelta(34516),
        tcaAdaptorMenloFcErrorStatsPushErrorsDeltaMin(34517),
        tcaAdaptorMenloFcErrorStatsPushErrorsDeltaMax(34518),
        tcaAdaptorMenloFcErrorStatsPushErrorsDeltaAvg(34519),
        tcaAdaptorMenloFcErrorStatsUncorrectableErrorsDelta(34526),
        tcaAdaptorMenloFcErrorStatsUncorrectableErrorsDeltaMin(34527),
        tcaAdaptorMenloFcErrorStatsUncorrectableErrorsDeltaMax(34528),
        tcaAdaptorMenloFcErrorStatsUncorrectableErrorsDeltaAvg(34529),
        tcaAdaptorMenloqstatsDropOverrunN0Delta(34542),
        tcaAdaptorMenloqstatsDropOverrunN0DeltaMin(34543),
        tcaAdaptorMenloqstatsDropOverrunN0DeltaMax(34544),
        tcaAdaptorMenloqstatsDropOverrunN0DeltaAvg(34545),
        tcaAdaptorMenloqstatsDropOverrunN1Delta(34552),
        tcaAdaptorMenloqstatsDropOverrunN1DeltaMin(34553),
        tcaAdaptorMenloqstatsDropOverrunN1DeltaMax(34554),
        tcaAdaptorMenloqstatsDropOverrunN1DeltaAvg(34555),
        tcaAdaptorMenloqstatsTruncateOverrunN0Delta(34562),
        tcaAdaptorMenloqstatsTruncateOverrunN0DeltaMin(34563),
        tcaAdaptorMenloqstatsTruncateOverrunN0DeltaMax(34564),
        tcaAdaptorMenloqstatsTruncateOverrunN0DeltaAvg(34565),
        tcaAdaptorMenloqstatsTruncateOverrunN1Delta(34572),
        tcaAdaptorMenloqstatsTruncateOverrunN1DeltaMin(34573),
        tcaAdaptorMenloqstatsTruncateOverrunN1DeltaMax(34574),
        tcaAdaptorMenloqstatsTruncateOverrunN1DeltaAvg(34575),
        tcaAdaptorMenloqerrorStatsCorrectableErrorsDelta(34588),
        tcaAdaptorMenloqerrorStatsCorrectableErrorsDeltaMin(34589),
        tcaAdaptorMenloqerrorStatsCorrectableErrorsDeltaMax(34590),
        tcaAdaptorMenloqerrorStatsCorrectableErrorsDeltaAvg(34591),
        tcaAdaptorMenloqerrorStatsPopErrorsDelta(34598),
        tcaAdaptorMenloqerrorStatsPopErrorsDeltaMin(34599),
        tcaAdaptorMenloqerrorStatsPopErrorsDeltaMax(34600),
        tcaAdaptorMenloqerrorStatsPopErrorsDeltaAvg(34601),
        tcaAdaptorMenloqerrorStatsPushErrorsDelta(34608),
        tcaAdaptorMenloqerrorStatsPushErrorsDeltaMin(34609),
        tcaAdaptorMenloqerrorStatsPushErrorsDeltaMax(34610),
        tcaAdaptorMenloqerrorStatsPushErrorsDeltaAvg(34611),
        tcaAdaptorMenloqerrorStatsUncorrectableErrorsDelta(34618),
        tcaAdaptorMenloqerrorStatsUncorrectableErrorsDeltaMin(34619),
        tcaAdaptorMenloqerrorStatsUncorrectableErrorsDeltaMax(34620),
        tcaAdaptorMenloqerrorStatsUncorrectableErrorsDeltaAvg(34621),
        tcaAdaptorMenloNetEgStatsLearnReqDropDelta(34633),
        tcaAdaptorMenloNetEgStatsLearnReqDropDeltaMin(34634),
        tcaAdaptorMenloNetEgStatsLearnReqDropDeltaMax(34635),
        tcaAdaptorMenloNetEgStatsLearnReqDropDeltaAvg(34636),
        tcaAdaptorMenloNetEgStatsDropCmdDelta(34643),
        tcaAdaptorMenloNetEgStatsDropCmdDeltaMin(34644),
        tcaAdaptorMenloNetEgStatsDropCmdDeltaMax(34645),
        tcaAdaptorMenloNetEgStatsDropCmdDeltaAvg(34646),
        tcaAdaptorMenloNetEgStatsDropLifCfgInvalidDelta(34653),
        tcaAdaptorMenloNetEgStatsDropLifCfgInvalidDeltaMin(34654),
        tcaAdaptorMenloNetEgStatsDropLifCfgInvalidDeltaMax(34655),
        tcaAdaptorMenloNetEgStatsDropLifCfgInvalidDeltaAvg(34656),
        tcaAdaptorMenloNetEgStatsDropLifMapNoHitDelta(34663),
        tcaAdaptorMenloNetEgStatsDropLifMapNoHitDeltaMin(34664),
        tcaAdaptorMenloNetEgStatsDropLifMapNoHitDeltaMax(34665),
        tcaAdaptorMenloNetEgStatsDropLifMapNoHitDeltaAvg(34666),
        tcaAdaptorMenloNetEgStatsDropSrcBindDelta(34673),
        tcaAdaptorMenloNetEgStatsDropSrcBindDeltaMin(34674),
        tcaAdaptorMenloNetEgStatsDropSrcBindDeltaMax(34675),
        tcaAdaptorMenloNetEgStatsDropSrcBindDeltaAvg(34676),
        tcaAdaptorMenloNetInStatsFwdLookupNoHitDelta(34688),
        tcaAdaptorMenloNetInStatsFwdLookupNoHitDeltaMin(34689),
        tcaAdaptorMenloNetInStatsFwdLookupNoHitDeltaMax(34690),
        tcaAdaptorMenloNetInStatsFwdLookupNoHitDeltaAvg(34691),
        tcaAdaptorMenloNetInStatsDropFcMulticastDelta(34698),
        tcaAdaptorMenloNetInStatsDropFcMulticastDeltaMin(34699),
        tcaAdaptorMenloNetInStatsDropFcMulticastDeltaMax(34700),
        tcaAdaptorMenloNetInStatsDropFcMulticastDeltaAvg(34701),
        tcaAdaptorMenloNetInStatsDropFcLifInvalidDelta(34708),
        tcaAdaptorMenloNetInStatsDropFcLifInvalidDeltaMin(34709),
        tcaAdaptorMenloNetInStatsDropFcLifInvalidDeltaMax(34710),
        tcaAdaptorMenloNetInStatsDropFcLifInvalidDeltaAvg(34711),
        tcaAdaptorMenloNetInStatsDropNullPifDelta(34718),
        tcaAdaptorMenloNetInStatsDropNullPifDeltaMin(34719),
        tcaAdaptorMenloNetInStatsDropNullPifDeltaMax(34720),
        tcaAdaptorMenloNetInStatsDropNullPifDeltaAvg(34721),
        tcaAdaptorMenloHostPortStatsRxPausecfcdelta(34733),
        tcaAdaptorMenloHostPortStatsRxPausecfcdeltaMin(34734),
        tcaAdaptorMenloHostPortStatsRxPausecfcdeltaMax(34735),
        tcaAdaptorMenloHostPortStatsRxPausecfcdeltaAvg(34736),
        tcaAdaptorMenloHostPortStatsRxPausepfcdelta(34743),
        tcaAdaptorMenloHostPortStatsRxPausepfcdeltaMin(34744),
        tcaAdaptorMenloHostPortStatsRxPausepfcdeltaMax(34745),
        tcaAdaptorMenloHostPortStatsRxPausepfcdeltaAvg(34746),
        tcaAdaptorMenloHostPortStatsTxPausecfcdelta(34753),
        tcaAdaptorMenloHostPortStatsTxPausecfcdeltaMin(34754),
        tcaAdaptorMenloHostPortStatsTxPausecfcdeltaMax(34755),
        tcaAdaptorMenloHostPortStatsTxPausecfcdeltaAvg(34756),
        tcaAdaptorMenloHostPortStatsTxPausepfcdelta(34763),
        tcaAdaptorMenloHostPortStatsTxPausepfcdeltaMin(34764),
        tcaAdaptorMenloHostPortStatsTxPausepfcdeltaMax(34765),
        tcaAdaptorMenloHostPortStatsTxPausepfcdeltaAvg(34766),
        tcaAdaptorMenloDcePortStatsRxPausecfcdelta(34778),
        tcaAdaptorMenloDcePortStatsRxPausecfcdeltaMin(34779),
        tcaAdaptorMenloDcePortStatsRxPausecfcdeltaMax(34780),
        tcaAdaptorMenloDcePortStatsRxPausecfcdeltaAvg(34781),
        tcaAdaptorMenloDcePortStatsRxPausepfcdelta(34788),
        tcaAdaptorMenloDcePortStatsRxPausepfcdeltaMin(34789),
        tcaAdaptorMenloDcePortStatsRxPausepfcdeltaMax(34790),
        tcaAdaptorMenloDcePortStatsRxPausepfcdeltaAvg(34791),
        tcaAdaptorMenloDcePortStatsTxPausecfcdelta(34798),
        tcaAdaptorMenloDcePortStatsTxPausecfcdeltaMin(34799),
        tcaAdaptorMenloDcePortStatsTxPausecfcdeltaMax(34800),
        tcaAdaptorMenloDcePortStatsTxPausecfcdeltaAvg(34801),
        tcaAdaptorMenloDcePortStatsTxPausepfcdelta(34808),
        tcaAdaptorMenloDcePortStatsTxPausepfcdeltaMin(34809),
        tcaAdaptorMenloDcePortStatsTxPausepfcdeltaMax(34810),
        tcaAdaptorMenloDcePortStatsTxPausepfcdeltaAvg(34811),
        tcaAdaptorEtherIfStatsTxBytesDelta(34822),
        tcaAdaptorEtherIfStatsTxBytesDeltaMin(34823),
        tcaAdaptorEtherIfStatsTxBytesDeltaMax(34824),
        tcaAdaptorEtherIfStatsTxBytesDeltaAvg(34825),
        tcaAdaptorEtherIfStatsTxPacketsDelta(34832),
        tcaAdaptorEtherIfStatsTxPacketsDeltaMin(34833),
        tcaAdaptorEtherIfStatsTxPacketsDeltaMax(34834),
        tcaAdaptorEtherIfStatsTxPacketsDeltaAvg(34835),
        tcaAdaptorEtherIfStatsTxErrorsDelta(34842),
        tcaAdaptorEtherIfStatsTxErrorsDeltaMin(34843),
        tcaAdaptorEtherIfStatsTxErrorsDeltaMax(34844),
        tcaAdaptorEtherIfStatsTxErrorsDeltaAvg(34845),
        tcaAdaptorEtherIfStatsTxDroppedDelta(34852),
        tcaAdaptorEtherIfStatsTxDroppedDeltaMin(34853),
        tcaAdaptorEtherIfStatsTxDroppedDeltaMax(34854),
        tcaAdaptorEtherIfStatsTxDroppedDeltaAvg(34855),
        tcaAdaptorEtherIfStatsRxBytesDelta(34862),
        tcaAdaptorEtherIfStatsRxBytesDeltaMin(34863),
        tcaAdaptorEtherIfStatsRxBytesDeltaMax(34864),
        tcaAdaptorEtherIfStatsRxBytesDeltaAvg(34865),
        tcaAdaptorEtherIfStatsRxPacketsDelta(34872),
        tcaAdaptorEtherIfStatsRxPacketsDeltaMin(34873),
        tcaAdaptorEtherIfStatsRxPacketsDeltaMax(34874),
        tcaAdaptorEtherIfStatsRxPacketsDeltaAvg(34875),
        tcaAdaptorEtherIfStatsRxErrorsDelta(34882),
        tcaAdaptorEtherIfStatsRxErrorsDeltaMin(34883),
        tcaAdaptorEtherIfStatsRxErrorsDeltaMax(34884),
        tcaAdaptorEtherIfStatsRxErrorsDeltaAvg(34885),
        tcaAdaptorEtherIfStatsRxDroppedDelta(34892),
        tcaAdaptorEtherIfStatsRxDroppedDeltaMin(34893),
        tcaAdaptorEtherIfStatsRxDroppedDeltaMax(34894),
        tcaAdaptorEtherIfStatsRxDroppedDeltaAvg(34895),
        tcaAdaptorFcIfFrameStatsTxFramesDelta(34906),
        tcaAdaptorFcIfFrameStatsTxFramesDeltaMin(34907),
        tcaAdaptorFcIfFrameStatsTxFramesDeltaMax(34908),
        tcaAdaptorFcIfFrameStatsTxFramesDeltaAvg(34909),
        tcaAdaptorFcIfFrameStatsRxFramesDelta(34916),
        tcaAdaptorFcIfFrameStatsRxFramesDeltaMin(34917),
        tcaAdaptorFcIfFrameStatsRxFramesDeltaMax(34918),
        tcaAdaptorFcIfFrameStatsRxFramesDeltaAvg(34919),
        tcaAdaptorFcIfFrameStatsErrorFramesDelta(34926),
        tcaAdaptorFcIfFrameStatsErrorFramesDeltaMin(34927),
        tcaAdaptorFcIfFrameStatsErrorFramesDeltaMax(34928),
        tcaAdaptorFcIfFrameStatsErrorFramesDeltaAvg(34929),
        tcaAdaptorFcIfFrameStatsDumpedFramesDelta(34936),
        tcaAdaptorFcIfFrameStatsDumpedFramesDeltaMin(34937),
        tcaAdaptorFcIfFrameStatsDumpedFramesDeltaMax(34938),
        tcaAdaptorFcIfFrameStatsDumpedFramesDeltaAvg(34939),
        tcaAdaptorFcIfEventStatsLipCountDelta(34950),
        tcaAdaptorFcIfEventStatsLipCountDeltaMin(34951),
        tcaAdaptorFcIfEventStatsLipCountDeltaMax(34952),
        tcaAdaptorFcIfEventStatsLipCountDeltaAvg(34953),
        tcaAdaptorFcIfEventStatsInvalidcrccountDelta(34960),
        tcaAdaptorFcIfEventStatsInvalidcrccountDeltaMin(34961),
        tcaAdaptorFcIfEventStatsInvalidcrccountDeltaMax(34962),
        tcaAdaptorFcIfEventStatsInvalidcrccountDeltaAvg(34963),
        tcaAdaptorFcIfEventStatsNoscountDelta(34970),
        tcaAdaptorFcIfEventStatsNoscountDeltaMin(34971),
        tcaAdaptorFcIfEventStatsNoscountDeltaMax(34972),
        tcaAdaptorFcIfEventStatsNoscountDeltaAvg(34973),
        tcaAdaptorFcIfEventStatsLinkFailureCountDelta(34980),
        tcaAdaptorFcIfEventStatsLinkFailureCountDeltaMin(34981),
        tcaAdaptorFcIfEventStatsLinkFailureCountDeltaMax(34982),
        tcaAdaptorFcIfEventStatsLinkFailureCountDeltaAvg(34983),
        tcaAdaptorFcIfEventStatsLossOfSyncCountDelta(34990),
        tcaAdaptorFcIfEventStatsLossOfSyncCountDeltaMin(34991),
        tcaAdaptorFcIfEventStatsLossOfSyncCountDeltaMax(34992),
        tcaAdaptorFcIfEventStatsLossOfSyncCountDeltaAvg(34993),
        tcaAdaptorFcIfEventStatsLossOfSignalCountDelta(35000),
        tcaAdaptorFcIfEventStatsLossOfSignalCountDeltaMin(35001),
        tcaAdaptorFcIfEventStatsLossOfSignalCountDeltaMax(35002),
        tcaAdaptorFcIfEventStatsLossOfSignalCountDeltaAvg(35003),
        tcaAdaptorFcIfEventStatsSeqProtocolErrCountDelta(35010),
        tcaAdaptorFcIfEventStatsSeqProtocolErrCountDeltaMin(35011),
        tcaAdaptorFcIfEventStatsSeqProtocolErrCountDeltaMax(35012),
        tcaAdaptorFcIfEventStatsSeqProtocolErrCountDeltaAvg(35013),
        tcaAdaptorFcIfEventStatsSecondsSinceLastResetDelta(35020),
        tcaAdaptorFcIfEventStatsSecondsSinceLastResetDeltaMin(35021),
        tcaAdaptorFcIfEventStatsSecondsSinceLastResetDeltaMax(35022),
        tcaAdaptorFcIfEventStatsSecondsSinceLastResetDeltaAvg(35023),
        tcaSwEnvStatsMainBoardOutlet1(35166),
        tcaSwEnvStatsMainBoardOutlet1Min(35168),
        tcaSwEnvStatsMainBoardOutlet1Max(35169),
        tcaSwEnvStatsMainBoardOutlet1Avg(35170),
        tcaSwEnvStatsMainBoardOutlet2(35174),
        tcaSwEnvStatsMainBoardOutlet2Min(35176),
        tcaSwEnvStatsMainBoardOutlet2Max(35177),
        tcaSwEnvStatsMainBoardOutlet2Avg(35178),
        tcaSwEnvStatsFanCtrlrInlet1(35198),
        tcaSwEnvStatsFanCtrlrInlet1Min(35200),
        tcaSwEnvStatsFanCtrlrInlet1Max(35201),
        tcaSwEnvStatsFanCtrlrInlet1Avg(35202),
        tcaSwEnvStatsFanCtrlrInlet2(35206),
        tcaSwEnvStatsFanCtrlrInlet2Min(35208),
        tcaSwEnvStatsFanCtrlrInlet2Max(35209),
        tcaSwEnvStatsFanCtrlrInlet2Avg(35210),
        tcaSwEnvStatsFanCtrlrInlet3(35214),
        tcaSwEnvStatsFanCtrlrInlet3Min(35216),
        tcaSwEnvStatsFanCtrlrInlet3Max(35217),
        tcaSwEnvStatsFanCtrlrInlet3Avg(35218),
        tcaSwEnvStatsFanCtrlrInlet4(35222),
        tcaSwEnvStatsFanCtrlrInlet4Min(35224),
        tcaSwEnvStatsFanCtrlrInlet4Max(35225),
        tcaSwEnvStatsFanCtrlrInlet4Avg(35226),
        tcaSwSystemStatsMemAvailable(35234),
        tcaSwSystemStatsMemAvailableMin(35236),
        tcaSwSystemStatsMemAvailableMax(35237),
        tcaSwSystemStatsMemAvailableAvg(35238),
        tcaSwSystemStatsMemCached(35242),
        tcaSwSystemStatsMemCachedMin(35244),
        tcaSwSystemStatsMemCachedMax(35245),
        tcaSwSystemStatsMemCachedAvg(35246),
        tcaSwSystemStatsLoad(35250),
        tcaSwSystemStatsLoadMin(35252),
        tcaSwSystemStatsLoadMax(35253),
        tcaSwSystemStatsLoadAvg(35254),
        tcaEtherTxStatsTotalBytesDelta(35275),
        tcaEtherTxStatsTotalBytesDeltaMin(35276),
        tcaEtherTxStatsTotalBytesDeltaMax(35277),
        tcaEtherTxStatsTotalBytesDeltaAvg(35278),
        tcaEtherTxStatsTotalPacketsDelta(35285),
        tcaEtherTxStatsTotalPacketsDeltaMin(35286),
        tcaEtherTxStatsTotalPacketsDeltaMax(35287),
        tcaEtherTxStatsTotalPacketsDeltaAvg(35288),
        tcaEtherTxStatsMulticastPacketsDelta(35295),
        tcaEtherTxStatsMulticastPacketsDeltaMin(35296),
        tcaEtherTxStatsMulticastPacketsDeltaMax(35297),
        tcaEtherTxStatsMulticastPacketsDeltaAvg(35298),
        tcaEtherTxStatsBroadcastPacketsDelta(35305),
        tcaEtherTxStatsBroadcastPacketsDeltaMin(35306),
        tcaEtherTxStatsBroadcastPacketsDeltaMax(35307),
        tcaEtherTxStatsBroadcastPacketsDeltaAvg(35308),
        tcaEtherTxStatsJumboPacketsDelta(35315),
        tcaEtherTxStatsJumboPacketsDeltaMin(35316),
        tcaEtherTxStatsJumboPacketsDeltaMax(35317),
        tcaEtherTxStatsJumboPacketsDeltaAvg(35318),
        tcaEtherRxStatsTotalBytesDelta(35329),
        tcaEtherRxStatsTotalBytesDeltaMin(35330),
        tcaEtherRxStatsTotalBytesDeltaMax(35331),
        tcaEtherRxStatsTotalBytesDeltaAvg(35332),
        tcaEtherRxStatsTotalPacketsDelta(35339),
        tcaEtherRxStatsTotalPacketsDeltaMin(35340),
        tcaEtherRxStatsTotalPacketsDeltaMax(35341),
        tcaEtherRxStatsTotalPacketsDeltaAvg(35342),
        tcaEtherRxStatsUnicastPacketsDelta(35349),
        tcaEtherRxStatsUnicastPacketsDeltaMin(35350),
        tcaEtherRxStatsUnicastPacketsDeltaMax(35351),
        tcaEtherRxStatsUnicastPacketsDeltaAvg(35352),
        tcaEtherRxStatsMulticastPacketsDelta(35359),
        tcaEtherRxStatsMulticastPacketsDeltaMin(35360),
        tcaEtherRxStatsMulticastPacketsDeltaMax(35361),
        tcaEtherRxStatsMulticastPacketsDeltaAvg(35362),
        tcaEtherRxStatsBroadcastPacketsDelta(35369),
        tcaEtherRxStatsBroadcastPacketsDeltaMin(35370),
        tcaEtherRxStatsBroadcastPacketsDeltaMax(35371),
        tcaEtherRxStatsBroadcastPacketsDeltaAvg(35372),
        tcaEtherRxStatsJumboPacketsDelta(35379),
        tcaEtherRxStatsJumboPacketsDeltaMin(35380),
        tcaEtherRxStatsJumboPacketsDeltaMax(35381),
        tcaEtherRxStatsJumboPacketsDeltaAvg(35382),
        tcaComputeMbPowerStatsConsumedPower(35962),
        tcaComputeMbPowerStatsConsumedPowerMin(35964),
        tcaComputeMbPowerStatsConsumedPowerMax(35965),
        tcaComputeMbPowerStatsConsumedPowerAvg(35966),
        tcaComputeMbTempStatsFmTempSenIo(35974),
        tcaComputeMbTempStatsFmTempSenIoMin(35976),
        tcaComputeMbTempStatsFmTempSenIoMax(35977),
        tcaComputeMbTempStatsFmTempSenIoAvg(35978),
        tcaEquipmentChassisStatsInputPower(36234),
        tcaEquipmentChassisStatsInputPowerMin(36236),
        tcaEquipmentChassisStatsInputPowerMax(36237),
        tcaEquipmentChassisStatsInputPowerAvg(36238),
        tcaEquipmentChassisStatsOutputPower(36242),
        tcaEquipmentChassisStatsOutputPowerMin(36244),
        tcaEquipmentChassisStatsOutputPowerMax(36245),
        tcaEquipmentChassisStatsOutputPowerAvg(36246),
        tcaEquipmentPsuStatsAmbientTemp(36266),
        tcaEquipmentPsuStatsAmbientTempMin(36268),
        tcaEquipmentPsuStatsAmbientTempMax(36269),
        tcaEquipmentPsuStatsAmbientTempAvg(36270),
        tcaEquipmentPsuStatsOutputCurrent(36274),
        tcaEquipmentPsuStatsOutputCurrentMin(36276),
        tcaEquipmentPsuStatsOutputCurrentMax(36277),
        tcaEquipmentPsuStatsOutputCurrentAvg(36278),
        tcaEquipmentPsuStatsOutputPower(36282),
        tcaEquipmentPsuStatsOutputPowerMin(36284),
        tcaEquipmentPsuStatsOutputPowerMax(36285),
        tcaEquipmentPsuStatsOutputPowerAvg(36286),
        tcaEquipmentPsuInputStatsCurrent(36294),
        tcaEquipmentPsuInputStatsCurrentMin(36296),
        tcaEquipmentPsuInputStatsCurrentMax(36297),
        tcaEquipmentPsuInputStatsCurrentAvg(36298),
        tcaEquipmentPsuInputStatsVoltage(36302),
        tcaEquipmentPsuInputStatsVoltageMin(36304),
        tcaEquipmentPsuInputStatsVoltageMax(36305),
        tcaEquipmentPsuInputStatsVoltageAvg(36306),
        tcaEquipmentPsuInputStatsPower(36310),
        tcaEquipmentPsuInputStatsPowerMin(36312),
        tcaEquipmentPsuInputStatsPowerMax(36313),
        tcaEquipmentPsuInputStatsPowerAvg(36314),
        tcaEquipmentFanModuleStatsAmbientTemp(36323),
        tcaEquipmentFanModuleStatsAmbientTempMin(36325),
        tcaEquipmentFanModuleStatsAmbientTempMax(36326),
        tcaEquipmentFanModuleStatsAmbientTempAvg(36327),
        tcaEquipmentFanStatsSpeed(36335),
        tcaEquipmentFanStatsSpeedMin(36337),
        tcaEquipmentFanStatsSpeedMax(36338),
        tcaEquipmentFanStatsSpeedAvg(36339),
        tcaEquipmentPsuStatsOutput12v(37154),
        tcaEquipmentPsuStatsOutput12vMin(37156),
        tcaEquipmentPsuStatsOutput12vMax(37157),
        tcaEquipmentPsuStatsOutput12vAvg(37158),
        tcaEquipmentPsuStatsOutput3v3(37162),
        tcaEquipmentPsuStatsOutput3v3Min(37164),
        tcaEquipmentPsuStatsOutput3v3Max(37165),
        tcaEquipmentPsuStatsOutput3v3Avg(37166),
        tcaEquipmentPsuStatsInput210v(37170),
        tcaEquipmentPsuStatsInput210vMin(37172),
        tcaEquipmentPsuStatsInput210vMax(37173),
        tcaEquipmentPsuStatsInput210vAvg(37174),
        tcaEquipmentIocardStatsAmbientTemp(37269),
        tcaEquipmentIocardStatsAmbientTempMin(37271),
        tcaEquipmentIocardStatsAmbientTempMax(37272),
        tcaEquipmentIocardStatsAmbientTempAvg(37273),
        tcaEtherErrStatsAlignDelta(37313),
        tcaEtherErrStatsAlignDeltaMin(37314),
        tcaEtherErrStatsAlignDeltaMax(37315),
        tcaEtherErrStatsAlignDeltaAvg(37316),
        tcaEtherErrStatsFcsDelta(37323),
        tcaEtherErrStatsFcsDeltaMin(37324),
        tcaEtherErrStatsFcsDeltaMax(37325),
        tcaEtherErrStatsFcsDeltaAvg(37326),
        tcaEtherErrStatsXmitDelta(37333),
        tcaEtherErrStatsXmitDeltaMin(37334),
        tcaEtherErrStatsXmitDeltaMax(37335),
        tcaEtherErrStatsXmitDeltaAvg(37336),
        tcaEtherErrStatsRcvDelta(37343),
        tcaEtherErrStatsRcvDeltaMin(37344),
        tcaEtherErrStatsRcvDeltaMax(37345),
        tcaEtherErrStatsRcvDeltaAvg(37346),
        tcaEtherErrStatsUnderSizeDelta(37353),
        tcaEtherErrStatsUnderSizeDeltaMin(37354),
        tcaEtherErrStatsUnderSizeDeltaMax(37355),
        tcaEtherErrStatsUnderSizeDeltaAvg(37356),
        tcaEtherErrStatsOutDiscardDelta(37363),
        tcaEtherErrStatsOutDiscardDeltaMin(37364),
        tcaEtherErrStatsOutDiscardDeltaMax(37365),
        tcaEtherErrStatsOutDiscardDeltaAvg(37366),
        tcaEtherErrStatsIntMacTxDelta(37383),
        tcaEtherErrStatsIntMacTxDeltaMin(37384),
        tcaEtherErrStatsIntMacTxDeltaMax(37385),
        tcaEtherErrStatsIntMacTxDeltaAvg(37386),
        tcaEtherErrStatsIntMacRxDelta(37393),
        tcaEtherErrStatsIntMacRxDeltaMin(37394),
        tcaEtherErrStatsIntMacRxDeltaMax(37395),
        tcaEtherErrStatsIntMacRxDeltaAvg(37396),
        tcaEtherLossStatsSingleCollisionDelta(37403),
        tcaEtherLossStatsSingleCollisionDeltaMin(37404),
        tcaEtherLossStatsSingleCollisionDeltaMax(37405),
        tcaEtherLossStatsSingleCollisionDeltaAvg(37406),
        tcaEtherLossStatsMultiCollisionDelta(37413),
        tcaEtherLossStatsMultiCollisionDeltaMin(37414),
        tcaEtherLossStatsMultiCollisionDeltaMax(37415),
        tcaEtherLossStatsMultiCollisionDeltaAvg(37416),
        tcaEtherLossStatsLateCollisionDelta(37423),
        tcaEtherLossStatsLateCollisionDeltaMin(37424),
        tcaEtherLossStatsLateCollisionDeltaMax(37425),
        tcaEtherLossStatsLateCollisionDeltaAvg(37426),
        tcaEtherLossStatsCarrierSenseDelta(37443),
        tcaEtherLossStatsCarrierSenseDeltaMin(37444),
        tcaEtherLossStatsCarrierSenseDeltaMax(37445),
        tcaEtherLossStatsCarrierSenseDeltaAvg(37446),
        tcaEtherLossStatsGiantsDelta(37453),
        tcaEtherLossStatsGiantsDeltaMin(37454),
        tcaEtherLossStatsGiantsDeltaMax(37455),
        tcaEtherLossStatsGiantsDeltaAvg(37456),
        tcaEtherLossStatsSymbolDelta(37463),
        tcaEtherLossStatsSymbolDeltaMin(37464),
        tcaEtherLossStatsSymbolDeltaMax(37465),
        tcaEtherLossStatsSymbolDeltaAvg(37466),
        tcaEtherLossStatsSqetestDelta(37473),
        tcaEtherLossStatsSqetestDeltaMin(37474),
        tcaEtherLossStatsSqetestDeltaMax(37475),
        tcaEtherLossStatsSqetestDeltaAvg(37476),
        tcaEtherPauseStatsRecvPauseDelta(37485),
        tcaEtherPauseStatsRecvPauseDeltaMin(37486),
        tcaEtherPauseStatsRecvPauseDeltaMax(37487),
        tcaEtherPauseStatsRecvPauseDeltaAvg(37488),
        tcaEtherPauseStatsXmitPauseDelta(37495),
        tcaEtherPauseStatsXmitPauseDeltaMin(37496),
        tcaEtherPauseStatsXmitPauseDeltaMax(37497),
        tcaEtherPauseStatsXmitPauseDeltaAvg(37498),
        tcaEtherPauseStatsResetsDelta(37505),
        tcaEtherPauseStatsResetsDeltaMin(37506),
        tcaEtherPauseStatsResetsDeltaMax(37507),
        tcaEtherPauseStatsResetsDeltaAvg(37508),
        tcaEtherLossStatsExcessCollisionDelta(37532),
        tcaEtherLossStatsExcessCollisionDeltaMin(37533),
        tcaEtherLossStatsExcessCollisionDeltaMax(37534),
        tcaEtherLossStatsExcessCollisionDeltaAvg(37535),
        tcaEtherTxStatsUnicastPacketsDelta(37543),
        tcaEtherTxStatsUnicastPacketsDeltaMin(37544),
        tcaEtherTxStatsUnicastPacketsDeltaMax(37545),
        tcaEtherTxStatsUnicastPacketsDeltaAvg(37546),
        tcaEtherErrStatsDeferredTxDelta(37553),
        tcaEtherErrStatsDeferredTxDeltaMin(37554),
        tcaEtherErrStatsDeferredTxDeltaMax(37555),
        tcaEtherErrStatsDeferredTxDeltaAvg(37556),
        tcaComputeMbPowerStatsInputVoltage(37564),
        tcaComputeMbPowerStatsInputVoltageMin(37566),
        tcaComputeMbPowerStatsInputVoltageMax(37567),
        tcaComputeMbPowerStatsInputVoltageAvg(37568),
        tcaComputeMbPowerStatsInputCurrent(37572),
        tcaComputeMbPowerStatsInputCurrentMin(37574),
        tcaComputeMbPowerStatsInputCurrentMax(37575),
        tcaComputeMbPowerStatsInputCurrentAvg(37576),
        tcaComputeMbTempStatsFmTempSenRear(37580),
        tcaComputeMbTempStatsFmTempSenRearMin(37582),
        tcaComputeMbTempStatsFmTempSenRearMax(37583),
        tcaComputeMbTempStatsFmTempSenRearAvg(37584),
        tcaMemoryUnitEnvStatsTemperature(37600),
        tcaMemoryUnitEnvStatsTemperatureMin(37602),
        tcaMemoryUnitEnvStatsTemperatureMax(37603),
        tcaMemoryUnitEnvStatsTemperatureAvg(37604),
        tcaProcessorEnvStatsTemperature(37610),
        tcaProcessorEnvStatsTemperatureMin(37612),
        tcaProcessorEnvStatsTemperatureMax(37613),
        tcaProcessorEnvStatsTemperatureAvg(37614),
        tcaSwEnvStatsPsuCtrlrInlet1(37771),
        tcaSwEnvStatsPsuCtrlrInlet1Min(37773),
        tcaSwEnvStatsPsuCtrlrInlet1Max(37774),
        tcaSwEnvStatsPsuCtrlrInlet1Avg(37775),
        tcaSwEnvStatsPsuCtrlrInlet2(37779),
        tcaSwEnvStatsPsuCtrlrInlet2Min(37781),
        tcaSwEnvStatsPsuCtrlrInlet2Max(37782),
        tcaSwEnvStatsPsuCtrlrInlet2Avg(37783),
        tcaComputePcieFatalProtocolStatsDllpErrors(38022),
        tcaComputePcieFatalProtocolStatsFlowControlErrors(38032),
        tcaComputePcieFatalReceiveStatsUnsupportedRequestErrors(38044),
        tcaComputePcieFatalReceiveStatsErrFatalErrors(38054),
        tcaComputePcieFatalReceiveStatsErrNonFatalErrors(38064),
        tcaComputePcieFatalCompletionStatsUnexpectedErrors(38086),
        tcaComputePcieFatalCompletionStatsTimeoutErrors(38096),
        tcaComputePcieFatalCompletionStatsAbortErrors(38106),
        tcaComputePcieFatalStatsSurpriseLinkDownErrors(38128),
        tcaComputePcieFatalStatsPoisonedtlperrors(38138),
        tcaComputePcieFatalStatsAcsViolationErrors(38148),
        tcaComputePcieFatalStatsMalformedtlperrors(38158),
        tcaEquipmentIocardStatsTemp(38311),
        tcaEquipmentIocardStatsTempMin(38313),
        tcaEquipmentIocardStatsTempMax(38314),
        tcaEquipmentIocardStatsTempAvg(38315),
        tcaProcessorEnvStatsInputCurrent(38349),
        tcaProcessorEnvStatsInputCurrentMin(38351),
        tcaProcessorEnvStatsInputCurrentMax(38352),
        tcaProcessorEnvStatsInputCurrentAvg(38353),
        tcaMemoryArrayEnvStatsInputCurrent(38357),
        tcaMemoryArrayEnvStatsInputCurrentMin(38359),
        tcaMemoryArrayEnvStatsInputCurrentMax(38360),
        tcaMemoryArrayEnvStatsInputCurrentAvg(38361),
        tcaAdaptorEthPortBySizeLargeStatsNoBreakdownGreaterThan1518Delta(38470),
        tcaAdaptorEthPortBySizeLargeStatsNoBrkdnGreaterThan1518DeltaMin(38471),
        tcaAdaptorEthPortBySizeLargeStatsNoBrkdnGreaterThan1518DeltaMax(38472),
        tcaAdaptorEthPortBySizeLargeStatsNoBrkdnGreaterThan1518DeltaAvg(38473),
        tcaPowerGroupStatsPower(38557),
        tcaPowerGroupStatsPowerMin(38559),
        tcaPowerGroupStatsPowerMax(38560),
        tcaPowerGroupStatsPowerAvg(38561),
        tcaMemoryBufferUnitEnvStatsTemperature(38624),
        tcaMemoryBufferUnitEnvStatsTemperatureMin(38626),
        tcaMemoryBufferUnitEnvStatsTemperatureMax(38627),
        tcaMemoryBufferUnitEnvStatsTemperatureAvg(38628),
        tcaComputeIohubEnvStatsTemperature(38678),
        tcaComputeIohubEnvStatsTemperatureMin(38680),
        tcaComputeIohubEnvStatsTemperatureMax(38681),
        tcaComputeIohubEnvStatsTemperatureAvg(38682),
        tcaComputeMbTempStatsFmTempSenRearl(39082),
        tcaComputeMbTempStatsFmTempSenRearlmin(39084),
        tcaComputeMbTempStatsFmTempSenRearlmax(39085),
        tcaComputeMbTempStatsFmTempSenRearlavg(39086),
        tcaComputeMbTempStatsFmTempSenRearr(39090),
        tcaComputeMbTempStatsFmTempSenRearrmin(39092),
        tcaComputeMbTempStatsFmTempSenRearrmax(39093),
        tcaComputeMbTempStatsFmTempSenRearravg(39094),
        tcaEquipmentFexEnvStatsOutlet1(39107),
        tcaEquipmentFexEnvStatsOutlet1Min(39109),
        tcaEquipmentFexEnvStatsOutlet1Max(39110),
        tcaEquipmentFexEnvStatsOutlet1Avg(39111),
        tcaEquipmentFexEnvStatsOutlet2(39115),
        tcaEquipmentFexEnvStatsOutlet2Min(39117),
        tcaEquipmentFexEnvStatsOutlet2Max(39118),
        tcaEquipmentFexEnvStatsOutlet2Avg(39119),
        tcaEquipmentFexEnvStatsInlet(39123),
        tcaEquipmentFexEnvStatsInletMin(39125),
        tcaEquipmentFexEnvStatsInletMax(39126),
        tcaEquipmentFexEnvStatsInletAvg(39127),
        tcaEquipmentFexEnvStatsInlet1(39131),
        tcaEquipmentFexEnvStatsInlet1Min(39133),
        tcaEquipmentFexEnvStatsInlet1Max(39134),
        tcaEquipmentFexEnvStatsInlet1Avg(39135),
        tcaEquipmentFexEnvStatsDie1(39139),
        tcaEquipmentFexEnvStatsDie1Min(39141),
        tcaEquipmentFexEnvStatsDie1Max(39142),
        tcaEquipmentFexEnvStatsDie1Avg(39143),
        tcaEquipmentFexPowerSummaryTotalPower(39166),
        tcaEquipmentFexPowerSummaryTotalPowerMin(39168),
        tcaEquipmentFexPowerSummaryTotalPowerMax(39169),
        tcaEquipmentFexPowerSummaryTotalPowerAvg(39170),
        tcaEquipmentFexPowerSummaryReservedPower(39174),
        tcaEquipmentFexPowerSummaryReservedPowerMin(39176),
        tcaEquipmentFexPowerSummaryReservedPowerMax(39177),
        tcaEquipmentFexPowerSummaryReservedPowerAvg(39178),
        tcaEquipmentFexPowerSummaryModulePower(39182),
        tcaEquipmentFexPowerSummaryModulePowerMin(39184),
        tcaEquipmentFexPowerSummaryModulePowerMax(39185),
        tcaEquipmentFexPowerSummaryModulePowerAvg(39186),
        tcaEquipmentFexPowerSummaryAvailablePower(39190),
        tcaEquipmentFexPowerSummaryAvailablePowerMin(39192),
        tcaEquipmentFexPowerSummaryAvailablePowerMax(39193),
        tcaEquipmentFexPowerSummaryAvailablePowerAvg(39194),
        tcaEquipmentFexPsuInputStatsCurrent(39200),
        tcaEquipmentFexPsuInputStatsCurrentMin(39202),
        tcaEquipmentFexPsuInputStatsCurrentMax(39203),
        tcaEquipmentFexPsuInputStatsCurrentAvg(39204),
        tcaEquipmentFexPsuInputStatsVoltage(39208),
        tcaEquipmentFexPsuInputStatsVoltageMin(39210),
        tcaEquipmentFexPsuInputStatsVoltageMax(39211),
        tcaEquipmentFexPsuInputStatsVoltageAvg(39212),
        tcaEquipmentFexPsuInputStatsPower(39216),
        tcaEquipmentFexPsuInputStatsPowerMin(39218),
        tcaEquipmentFexPsuInputStatsPowerMax(39219),
        tcaEquipmentFexPsuInputStatsPowerAvg(39220),
        tcaEquipmentRackUnitPsuStatsAmbientTemp(39227),
        tcaEquipmentRackUnitPsuStatsAmbientTempMin(39229),
        tcaEquipmentRackUnitPsuStatsAmbientTempMax(39230),
        tcaEquipmentRackUnitPsuStatsAmbientTempAvg(39231),
        tcaEquipmentRackUnitPsuStatsOutputCurrent(39235),
        tcaEquipmentRackUnitPsuStatsOutputCurrentMin(39237),
        tcaEquipmentRackUnitPsuStatsOutputCurrentMax(39238),
        tcaEquipmentRackUnitPsuStatsOutputCurrentAvg(39239),
        tcaEquipmentRackUnitPsuStatsOutputPower(39243),
        tcaEquipmentRackUnitPsuStatsOutputPowerMin(39245),
        tcaEquipmentRackUnitPsuStatsOutputPowerMax(39246),
        tcaEquipmentRackUnitPsuStatsOutputPowerAvg(39247),
        tcaEquipmentRackUnitPsuStatsInputPower(39251),
        tcaEquipmentRackUnitPsuStatsInputPowerMin(39253),
        tcaEquipmentRackUnitPsuStatsInputPowerMax(39254),
        tcaEquipmentRackUnitPsuStatsInputPowerAvg(39255),
        tcaEquipmentRackUnitPsuStatsOutputVoltage(39259),
        tcaEquipmentRackUnitPsuStatsOutputVoltageMin(39261),
        tcaEquipmentRackUnitPsuStatsOutputVoltageMax(39262),
        tcaEquipmentRackUnitPsuStatsOutputVoltageAvg(39263),
        tcaEquipmentRackUnitPsuStatsInputVoltage(39267),
        tcaEquipmentRackUnitPsuStatsInputVoltageMin(39269),
        tcaEquipmentRackUnitPsuStatsInputVoltageMax(39270),
        tcaEquipmentRackUnitPsuStatsInputVoltageAvg(39271),
        tcaComputePcieFatalReceiveStatsBufferOverflowErrors(39583),
        tcaProcessorErrorStatsMirroringIntraSockErrors(39649),
        tcaProcessorErrorStatsMirroringInterSockErrors(39658),
        tcaProcessorErrorStatsSparingErrors(39667),
        tcaProcessorErrorStatsSmiLinkCorrErrors(39676),
        tcaProcessorErrorStatsSmiLinkUncorrErrors(39685),
        tcaMemoryErrorStatsEccMultibitErrors(39702),
        tcaMemoryErrorStatsEccSinglebitErrors(39711),
        tcaMemoryErrorStatsAddressParityErrors(39720),
        tcaMemoryErrorStatsMismatchErrors(39729),
        tcaEquipmentRackUnitFanStatsSpeed(39794),
        tcaEquipmentRackUnitFanStatsSpeedMin(39796),
        tcaEquipmentRackUnitFanStatsSpeedMax(39797),
        tcaEquipmentRackUnitFanStatsSpeedAvg(39798),
        tcaComputeRackUnitMbTempStatsFrontTemp(40092),
        tcaComputeRackUnitMbTempStatsFrontTempMin(40094),
        tcaComputeRackUnitMbTempStatsFrontTempMax(40095),
        tcaComputeRackUnitMbTempStatsFrontTempAvg(40096),
        tcaComputeRackUnitMbTempStatsRearTemp(40100),
        tcaComputeRackUnitMbTempStatsRearTempMin(40102),
        tcaComputeRackUnitMbTempStatsRearTempMax(40103),
        tcaComputeRackUnitMbTempStatsRearTempAvg(40104),
        tcaComputeRackUnitMbTempStatsAmbientTemp(40108),
        tcaComputeRackUnitMbTempStatsAmbientTempMin(40110),
        tcaComputeRackUnitMbTempStatsAmbientTempMax(40111),
        tcaComputeRackUnitMbTempStatsAmbientTempAvg(40112),
        tcaComputeRackUnitMbTempStatsIoh1Temp(40116),
        tcaComputeRackUnitMbTempStatsIoh1TempMin(40118),
        tcaComputeRackUnitMbTempStatsIoh1TempMax(40119),
        tcaComputeRackUnitMbTempStatsIoh1TempAvg(40120),
        tcaComputeRackUnitMbTempStatsIoh2Temp(40124),
        tcaComputeRackUnitMbTempStatsIoh2TempMin(40126),
        tcaComputeRackUnitMbTempStatsIoh2TempMax(40127),
        tcaComputeRackUnitMbTempStatsIoh2TempAvg(40128),
        fsmFePresenceRemoteInv(77845),
        fsmFeConnRemoteInv(77846),
        fsmRemoveChassisRemoteInv(77847),
        fsmSetLocatorLedRemoteInv(77848),
        fsmExtMgmtIfConfigRemoteInv(77958),
        fsmIdentifyRemoteInv(77959),
        fsmPsuPolicyConfigRemoteInv(77973),
        fsmResetFcPersBindingRemoteInv(77974),
        fsmDiagRemoteInv(77975),
        fsmSwitchModeRemoteInv(77979),
        fsmUpdateSvcEpRemoteInv(78016),
        fsmRestartWebSvcRemoteInv(78017),
        fsmUpdateEpRemoteInv(78019),
        fsmUpdateRealmRemoteInv(78020),
        fsmUpdateUserEpRemoteInv(78021),
        fsmSingleRemoteInv(78040),
        fsmGlobalRemoteInv(78041),
        fsmExportRemoteInv(78044),
        fsmLogControlPersistRemoteInv(78046),
        fsmCreateRemoteInv(78081),
        fsmDownloadRemoteInv(78090),
        fsmDeleteRemoteInv(78091),
        fsmUpdateSwitchRemoteInv(78093),
        fsmUpdateiomRemoteInv(78094),
        fsmActivateiomRemoteInv(78095),
        fsmUpdatebmcRemoteInv(78096),
        fsmActivatebmcRemoteInv(78097),
        fsmConfigCallhomeRemoteInv(78110),
        fsmSwMgmtOobIfConfigRemoteInv(78113),
        fsmSwMgmtInbandIfConfigRemoteInv(78114),
        fsmVirtualIfConfigRemoteInv(78119),
        fsmEnableVipRemoteInv(78120),
        fsmDisableVipRemoteInv(78121),
        fsmEnablehaRemoteInv(78122),
        fsmBackupRemoteInv(78123),
        fsmImportRemoteInv(78124),
        fsmConfigGlobalQoSremoteInv(78185),
        fsmRemoveRemoteInv(78190),
        fsmResetCmcRemoteInv(78243),
        fsmUpdateucsmanagerRemoteInv(78255),
        fsmSysConfigRemoteInv(78263),
        fsmPathResetRemoteInv(78292),
        fsmCircuitResetRemoteInv(78297),
        fsmConfigRemoteInv(78319),
        fsmCertInstallRemoteInv(78320),
        fsmRemoveProviderRemoteInv(78321),
        fsmUpdaterRemoteInv(78344),
        fsmDiscoverRemoteInv(78360),
        fsmAssociateRemoteInv(78361),
        fsmDisassociateRemoteInv(78362),
        fsmDecommissionRemoteInv(78364),
        fsmSoftShutdownRemoteInv(78365),
        fsmHardShutdownRemoteInv(78366),
        fsmTurnupRemoteInv(78367),
        fsmPowercycleRemoteInv(78368),
        fsmHardresetRemoteInv(78369),
        fsmSoftresetRemoteInv(78370),
        fsmSwConnUpdRemoteInv(78371),
        fsmBiosRecoveryRemoteInv(78372),
        fsmCmosResetRemoteInv(78374),
        fsmResetBmcRemoteInv(78375),
        fsmUpdateExtUsersRemoteInv(78378),
        fsmUpdateAdaptorRemoteInv(78379),
        fsmActivateAdaptorRemoteInv(78380),
        fsmConfigSoLremoteInv(78381),
        fsmUnconfigSoLremoteInv(78382),
        fsmSetFeLocatorLedRemoteInv(78383),
        fsmPowerCapRemoteInv(78390),
        fsmUpdateBoardControllerRemoteInv(78404),
        fsmDeployCatalogueRemoteInv(78405),
        fsmInstallRemoteInv(78431),
        fsmClearRemoteInv(78432),
        fsmUpdateFlexlmRemoteInv(78433),
        fsmRemoveFexRemoteInv(78447),
        fsmInitiateRemoteInv(78452),
        fsmDeleteTechSupFileRemoteInv(78453),
        fsmActivateCatalogRemoteInv(78457),
        fsmActivateMgmtExtRemoteInv(78458),
        fsmDeployRemoteInv(78490),
        fsmResetIomRemoteInv(78492),
        fsmConfigureRemoteInv(78500),
        fsmMuxOfflineRemoteInv(78501),
        fsmInCompatSfpPresenceRemoteInv(78529),
        fsmDiagnosticInterruptRemoteInv(78556),
        fsmDynamicReallocationRemoteInv(78574),
        fsmResetKvmRemoteInv(78603),
        fsmOnlineRemoteInv(78609),
        fsmOfflineRemoteInv(78610),
        fsmFePresenceFsmFail(999445),
        fsmFeConnFsmFail(999446),
        fsmRemoveChassisFsmFail(999447),
        fsmSetLocatorLedFsmFail(999448),
        fsmExtMgmtIfConfigFsmFail(999558),
        fsmIdentifyFsmFail(999559),
        fsmPsuPolicyConfigFsmFail(999573),
        fsmResetFcPersBindingFsmFail(999574),
        fsmDiagFsmFail(999575),
        fsmSwitchModeFsmFail(999579),
        fsmUpdateSvcEpFsmFail(999616),
        fsmRestartWebSvcFsmFail(999617),
        fsmUpdateEpFsmFail(999619),
        fsmUpdateRealmFsmFail(999620),
        fsmUpdateUserEpFsmFail(999621),
        fsmSingleFsmFail(999640),
        fsmGlobalFsmFail(999641),
        fsmExportFsmFail(999644),
        fsmLogControlPersistFsmFail(999646),
        fsmCreateFsmFail(999681),
        fsmDownloadFsmFail(999690),
        fsmDeleteFsmFail(999691),
        fsmUpdateSwitchFsmFail(999693),
        fsmUpdateiomFsmFail(999694),
        fsmActivateiomFsmFail(999695),
        fsmUpdatebmcFsmFail(999696),
        fsmActivatebmcFsmFail(999697),
        fsmConfigCallhomeFsmFail(999710),
        fsmSwMgmtOobIfConfigFsmFail(999713),
        fsmSwMgmtInbandIfConfigFsmFail(999714),
        fsmVirtualIfConfigFsmFail(999719),
        fsmEnableVipFsmFail(999720),
        fsmDisableVipFsmFail(999721),
        fsmEnablehaFsmFail(999722),
        fsmBackupFsmFail(999723),
        fsmImportFsmFail(999724),
        fsmConfigGlobalQoSfsmFail(999785),
        fsmRemoveFsmFail(999790),
        fsmResetCmcFsmFail(999843),
        fsmUpdateucsmanagerFsmFail(999855),
        fsmSysConfigFsmFail(999863),
        fsmPathResetFsmFail(999892),
        fsmCircuitResetFsmFail(999897),
        fsmConfigFsmFail(999919),
        fsmCertInstallFsmFail(999920),
        fsmRemoveProviderFsmFail(999921),
        fsmUpdaterFsmFail(999944),
        fsmDiscoverFsmFail(999960),
        fsmAssociateFsmFail(999961),
        fsmDisassociateFsmFail(999962),
        fsmDecommissionFsmFail(999964),
        fsmSoftShutdownFsmFail(999965),
        fsmHardShutdownFsmFail(999966),
        fsmTurnupFsmFail(999967),
        fsmPowercycleFsmFail(999968),
        fsmHardresetFsmFail(999969),
        fsmSoftresetFsmFail(999970),
        fsmSwConnUpdFsmFail(999971),
        fsmBiosRecoveryFsmFail(999972),
        fsmCmosResetFsmFail(999974),
        fsmResetBmcFsmFail(999975),
        fsmUpdateExtUsersFsmFail(999978),
        fsmUpdateAdaptorFsmFail(999979),
        fsmActivateAdaptorFsmFail(999980),
        fsmConfigSoLfsmFail(999981),
        fsmUnconfigSoLfsmFail(999982),
        fsmSetFeLocatorLedFsmFail(999983),
        fsmPowerCapFsmFail(999990),
        fsmUpdateBoardControllerFsmFail(1000004),
        fsmDeployCatalogueFsmFail(1000005),
        fsmInstallFsmFail(1000031),
        fsmClearFsmFail(1000032),
        fsmUpdateFlexlmFsmFail(1000033),
        fsmRemoveFexFsmFail(1000047),
        fsmInitiateFsmFail(1000052),
        fsmDeleteTechSupFileFsmFail(1000053),
        fsmActivateCatalogFsmFail(1000057),
        fsmActivateMgmtExtFsmFail(1000058),
        fsmDeployFsmFail(1000090),
        fsmResetIomFsmFail(1000092),
        fsmConfigureFsmFail(1000100),
        fsmMuxOfflineFsmFail(1000101),
        fsmInCompatSfpPresenceFsmFail(1000129),
        fsmDiagnosticInterruptFsmFail(1000156),
        fsmDynamicReallocationFsmFail(1000174),
        fsmResetKvmFsmFail(1000203),
        fsmOnlineFsmFail(1000209),
        fsmOfflineFsmFail(1000210),
        unrVnicTemplStatsPolicyName(4522530),
        unrVnicSanConnTemplQosPolicyName(4522532),
        unrVnicVnicStatsPolicyName(4522561),
        unrVnicProfileQosPolicyName(4522588),
        unrVnicFcNodeIdentPoolName(4522603),
        unrLsServerSrcTemplName(4525234),
        unrLsServerIdentPoolName(4525239),
        unrLsServerBootPolicyName(4525240),
        unrLsServerLocalDiskPolicyName(4525241),
        unrLsServerScrubPolicyName(4525247),
        unrLsServerDynamicConPolicyName(4525248),
        unrLsServerHostFwPolicyName(4525250),
        unrLsServerMgmtFwPolicyName(4525251),
        unrLsServerMgmtAccessPolicyName(4525252),
        unrLsServerSolPolicyName(4525253),
        unrLsServerStatsPolicyName(4525254),
        unrVnicEtherBaseQosPolicyName(4526517),
        unrVnicEtherBaseNwCtrlPolicyName(4526850),
        unrVnicProfileNwCtrlPolicyName(4526851),
        unrLsServerVconProfileName(4526901),
        unrLsServerBiosProfileName(4526902),
        unrLsServerPowerPolicyName(4528591),
        unrLsServerMaintPolicyName(4528596),
        unrVnicSanConnTemplIdentPoolName(4528609),
        unrVnicLanConnTemplNwCtrlPolicyName(4528611),
        unrVnicLanConnTemplIdentPoolName(4528613),
        unrVnicFcBaseAdaptorProfileName(4528616),
        unrVnicFcBaseIdentPoolName(4528618),
        unrVnicFcBaseNwTemplName(4528620),
        unrVnicEtherBaseAdaptorProfileName(4528623),
        unrVnicEtherBaseIdentPoolName(4528625),
        unrVnicEtherBaseNwTemplName(4528627),
        unrVnicLanConnTemplQosPolicyName(4528680),
        unrVnicFcBaseQosPolicyName(4528682)
    }

CucsConditionSeverity ::= TEXTUAL-CONVENTION
    STATUS        current
    DESCRIPTION
        ""
    SYNTAX        INTEGER {
        cleared(0),
        info(1),
        condition(2),
        warning(3),
        minor(4),
        major(5),
        critical(6)
    }

CucsConditionTag ::= TEXTUAL-CONVENTION
    STATUS        current
    DESCRIPTION
        ""
    SYNTAX        BITS {
        server(0),
        network(1),
        storage(2),
        pod(3),
        security(4),
        operations(5),
        fsmstagefail(6),
        fsmstageretry(7),
        fsmstageremoteinv(8)
    }

CucsConditionType ::= TEXTUAL-CONVENTION
    STATUS        current
    DESCRIPTION
        ""
    SYNTAX        INTEGER {
        generic(0),
        fsm(1),
        equipment(2),
        network(3),
        server(4),
        configuration(5),
        environmental(6),
        connectivity(7),
        operational(8),
        sysdebug(9)
    }

CucsDcxAdminState ::= TEXTUAL-CONVENTION
    STATUS        current
    DESCRIPTION
        ""
    SYNTAX        INTEGER {
        enabled(0),
        disabled(1)
    }

CucsDcxNsAllocStatus ::= TEXTUAL-CONVENTION
    STATUS        current
    DESCRIPTION
        ""
    SYNTAX        INTEGER {
        available(0),
        full(1),
        exceeded(2)
    }

CucsDcxOperState ::= TEXTUAL-CONVENTION
    STATUS        current
    DESCRIPTION
        ""
    SYNTAX        INTEGER {
        unknown(0),
        adminDown(1),
        linkDown(2),
        error(3),
        active(4),
        passive(5)
    }

CucsDcxProtState ::= TEXTUAL-CONVENTION
    STATUS        current
    DESCRIPTION
        ""
    SYNTAX        INTEGER {
        noProtection(0),
        active(1),
        passive(2)
    }

CucsDcxState ::= TEXTUAL-CONVENTION
    STATUS        current
    DESCRIPTION
        ""
    SYNTAX        INTEGER {
        unknown(0),
        present(1),
        creating(2),
        modifying(3),
        destroying(4),
        createPend(5),
        modifyPend(6),
        destroyPend(7)
    }

CucsDcxVIfProtRole ::= TEXTUAL-CONVENTION
    STATUS        current
    DESCRIPTION
        ""
    SYNTAX        INTEGER {
        unprotected(0),
        primary(1),
        backup(2)
    }

CucsDiagAdminState ::= TEXTUAL-CONVENTION
    STATUS        current
    DESCRIPTION
        ""
    SYNTAX        INTEGER {
        ready(0),
        trigger(1),
        cancel(2)
    }

CucsDiagBladeTestType ::= TEXTUAL-CONVENTION
    STATUS        current
    DESCRIPTION
        ""
    SYNTAX        INTEGER {
        disk(0),
        processor(1),
        memory(2),
        memtest(3),
        stress(4),
        pci(5)
    }

CucsDiagFailureAction ::= TEXTUAL-CONVENTION
    STATUS        current
    DESCRIPTION
        ""
    SYNTAX        BITS {
        techSupport(0),
        waitDebug(1),
        skipRemaining(2)
    }

CucsDiagNetworkTestType ::= TEXTUAL-CONVENTION
    STATUS        current
    DESCRIPTION
        ""
    SYNTAX        INTEGER {
        eth(0),
        fc(1)
    }

CucsDiagSrvCtrlType ::= TEXTUAL-CONVENTION
    STATUS        current
    DESCRIPTION
        ""
    SYNTAX        INTEGER {
        full(1),
        efi(33)
    }

CucsDiagStatus ::= TEXTUAL-CONVENTION
    STATUS        current
    DESCRIPTION
        ""
    SYNTAX        INTEGER {
        complete(0),
        inProgress(1),
        failed(2),
        notRun(3),
        cancelled(4),
        scheduled(5)
    }

CucsDiagStatusIssues ::= TEXTUAL-CONVENTION
    STATUS        current
    DESCRIPTION
        ""
    SYNTAX        BITS {
        testFailure(0),
        runCancelled(1),
        componentError(2),
        stagesCompleted(3)
    }

CucsDiagSuccessAction ::= TEXTUAL-CONVENTION
    STATUS        current
    DESCRIPTION
        ""
    SYNTAX        BITS {
        techSupport(0),
        waitDebug(1)
    }

CucsDiagTestOrder ::= TEXTUAL-CONVENTION
    STATUS        current
    DESCRIPTION
        ""
    SYNTAX        Gauge32 (1..64)

CucsDpsecForgedTransmit ::= TEXTUAL-CONVENTION
    STATUS        current
    DESCRIPTION
        ""
    SYNTAX        INTEGER {
        allow(0),
        deny(1)
    }

CucsEpqosDefinitionDelTaskFsmTaskItem ::= TEXTUAL-CONVENTION
    STATUS        current
    DESCRIPTION
        ""
    SYNTAX        INTEGER {
        nop(0),
        remove(319)
    }

CucsEpqosDefinitionFsmTaskItem ::= TEXTUAL-CONVENTION
    STATUS        current
    DESCRIPTION
        ""
    SYNTAX        INTEGER {
        nop(0),
        deploy(316)
    }

CucsEquipmentAdminPowerState ::= TEXTUAL-CONVENTION
    STATUS        current
    DESCRIPTION
        ""
    SYNTAX        INTEGER {
        policy(1),
        cycleImmediate(2),
        cycleWait(3)
    }

CucsEquipmentChassisId ::= TEXTUAL-CONVENTION
    STATUS        current
    DESCRIPTION
        ""
    SYNTAX        Gauge32 (1..255)

CucsEquipmentChassisAdminState ::= TEXTUAL-CONVENTION
    STATUS        current
    DESCRIPTION
        ""
    SYNTAX        INTEGER {
        acknowledged(1),
        reAcknowledge(2),
        decommission(3),
        remove(4)
    }

CucsEquipmentChassisConfigProgressIndicator ::= TEXTUAL-CONVENTION
    STATUS        current
    DESCRIPTION
        ""
    SYNTAX        INTEGER {
        ackNotInProgress(0),
        ackInProgress(1)
    }

CucsEquipmentChassisConfigState ::= TEXTUAL-CONVENTION
    STATUS        current
    DESCRIPTION
        ""
    SYNTAX        INTEGER {
        unInitialized(0),
        unAcknowledged(1),
        unsupportedConnectivity(2),
        ok(3),
        removing(4),
        ackInProgress(6)
    }

CucsEquipmentChassisFsmTaskItem ::= TEXTUAL-CONVENTION
    STATUS        current
    DESCRIPTION
        ""
    SYNTAX        INTEGER {
        nop(0),
        removeChassis(9),
        psuPolicyConfig(140),
        powerCap(829),
        dynamicReallocation(1048)
    }

CucsEquipmentChassisIssues ::= TEXTUAL-CONVENTION
    STATUS        current
    DESCRIPTION
        ""
    SYNTAX        BITS {
        chassisThermal(0),
        chassisInoperable(1),
        chassisVoltage(2),
        chassisPerf(3),
        chassisPower(4),
        removed(5),
        config(6),
        chassisPostFailure(7),
        psuThermal(8),
        psuInoperable(9),
        psuVoltage(10),
        psuPerf(11),
        psuPower(12),
        fanThermal(13),
        fanInoperable(14),
        fanVoltage(15),
        fanPerf(16),
        fanPower(17),
        iocardThermal(18),
        iocardInoperable(19),
        iocardVoltage(20),
        iocardPerf(21),
        iocardPower(22),
        computeThermal(23),
        computeInoperable(24),
        computeVoltage(25),
        computePerf(26),
        computePower(27),
        iocardInaccessible(28),
        fabricConnProblem(29),
        fabricUnsupportedConn(30),
        chassisLimitExceeded(31)
    }

CucsEquipmentChassisPowerOperState ::= TEXTUAL-CONVENTION
    STATUS        current
    DESCRIPTION
        ""
    SYNTAX        INTEGER {
        unknown(0),
        ok(1),
        failed(2),
        inputFailed(3),
        inputDegraded(4),
        outputFailed(5),
        outputDegraded(6),
        redundancyFailed(7),
        redundancyDegraded(8)
    }

CucsEquipmentChassisStatsThresholded ::= TEXTUAL-CONVENTION
    STATUS        current
    DESCRIPTION
        ""
    SYNTAX        BITS {
        inputPower(0),
        inputPowerAvg(1),
        inputPowerMax(2),
        inputPowerMin(3),
        outputPower(4),
        outputPowerAvg(5),
        outputPowerMax(6),
        outputPowerMin(7)
    }

CucsEquipmentChassisStatsHistThresholded ::= TEXTUAL-CONVENTION
    STATUS        current
    DESCRIPTION
        ""
    SYNTAX        BITS {
        inputPower(0),
        inputPowerAvg(1),
        inputPowerMax(2),
        inputPowerMin(3),
        outputPower(4),
        outputPowerAvg(5),
        outputPowerMax(6),
        outputPowerMin(7)
    }

CucsEquipmentCommStatus ::= TEXTUAL-CONVENTION
    STATUS        current
    DESCRIPTION
        ""
    SYNTAX        INTEGER {
        unknown(0),
        connected(1),
        disconnected(2)
    }

CucsEquipmentConnectionStatus ::= TEXTUAL-CONVENTION
    STATUS        current
    DESCRIPTION
        ""
    SYNTAX        BITS {
        a(0),
        b(1)
    }

CucsEquipmentDiscoveryState ::= TEXTUAL-CONVENTION
    STATUS        current
    DESCRIPTION
        ""
    SYNTAX        INTEGER {
        unknown(0),
        online(1),
        offline(2),
        discovered(3),
        unsupportedConnectivity(4),
        autoUpgrading(5)
    }

CucsEquipmentFanId ::= TEXTUAL-CONVENTION
    STATUS        current
    DESCRIPTION
        ""
    SYNTAX        Gauge32 (1..8)

CucsEquipmentFanModule ::= TEXTUAL-CONVENTION
    STATUS        current
    DESCRIPTION
        ""
    SYNTAX        Gauge32 (1..8)

CucsEquipmentFanTray ::= TEXTUAL-CONVENTION
    STATUS        current
    DESCRIPTION
        ""
    SYNTAX        Gauge32 (1..8)

CucsEquipmentFanModuleId ::= TEXTUAL-CONVENTION
    STATUS        current
    DESCRIPTION
        ""
    SYNTAX        Gauge32 (1..8)

CucsEquipmentFanModuleTray ::= TEXTUAL-CONVENTION
    STATUS        current
    DESCRIPTION
        ""
    SYNTAX        Gauge32 (1..1)

CucsEquipmentFanModuleStatsThresholded ::= TEXTUAL-CONVENTION
    STATUS        current
    DESCRIPTION
        ""
    SYNTAX        BITS {
        ambientTemp(0),
        ambientTempAvg(1),
        ambientTempMax(2),
        ambientTempMin(3)
    }

CucsEquipmentFanModuleStatsHistThresholded ::= TEXTUAL-CONVENTION
    STATUS        current
    DESCRIPTION
        ""
    SYNTAX        BITS {
        ambientTemp(0),
        ambientTempAvg(1),
        ambientTempMax(2),
        ambientTempMin(3)
    }

CucsEquipmentFanStatsThresholded ::= TEXTUAL-CONVENTION
    STATUS        current
    DESCRIPTION
        ""
    SYNTAX        BITS {
        speed(0),
        speedAvg(1),
        speedMax(2),
        speedMin(3)
    }

CucsEquipmentFanStatsHistThresholded ::= TEXTUAL-CONVENTION
    STATUS        current
    DESCRIPTION
        ""
    SYNTAX        BITS {
        speed(0),
        speedAvg(1),
        speedMax(2),
        speedMin(3)
    }

CucsEquipmentFexId ::= TEXTUAL-CONVENTION
    STATUS        current
    DESCRIPTION
        ""
    SYNTAX        Gauge32 (1..255)

CucsEquipmentFexEnvStatsThresholded ::= TEXTUAL-CONVENTION
    STATUS        current
    DESCRIPTION
        ""
    SYNTAX        BITS {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CucsEquipmentFexEnvStatsHistThresholded ::= TEXTUAL-CONVENTION
    STATUS        current
    DESCRIPTION
        ""
    SYNTAX        BITS {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CucsEquipmentFexFsmTaskItem ::= TEXTUAL-CONVENTION
    STATUS        current
    DESCRIPTION
        ""
    SYNTAX        INTEGER {
        nop(0),
        removeFex(887)
    }

CucsEquipmentFexPowerSummaryThresholded ::= TEXTUAL-CONVENTION
    STATUS        current
    DESCRIPTION
        ""
    SYNTAX        BITS {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CucsEquipmentFexPowerSummaryHistThresholded ::= TEXTUAL-CONVENTION
    STATUS        current
    DESCRIPTION
        ""
    SYNTAX        BITS {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CucsEquipmentFexPsuInputStatsThresholded ::= TEXTUAL-CONVENTION
    STATUS        current
    DESCRIPTION
        ""
    SYNTAX        BITS {
        current(0),
        currentAvg(1),
        currentMax(2),
        currentMin(3),
        power(4),
        powerAvg(5),
        powerMax(6),
        powerMin(7),
        voltage(8),
        voltageAvg(9),
        voltageMax(10),
        voltageMin(11)
    }

CucsEquipmentFexPsuInputStatsHistThresholded ::= TEXTUAL-CONVENTION
    STATUS        current
    DESCRIPTION
        ""
    SYNTAX        BITS {
        current(0),
        currentAvg(1),
        currentMax(2),
        currentMin(3),
        power(4),
        powerAvg(5),
        powerMax(6),
        powerMin(7),
        voltage(8),
        voltageAvg(9),
        voltageMax(10),
        voltageMin(11)
    }

CucsEquipmentIOCardId ::= TEXTUAL-CONVENTION
    STATUS        current
    DESCRIPTION
        ""
    SYNTAX        Gauge32 (1..2)

CucsEquipmentIOCardFsmTaskItem ::= TEXTUAL-CONVENTION
    STATUS        current
    DESCRIPTION
        ""
    SYNTAX        INTEGER {
        nop(0),
        fePresence(1),
        feConn(3),
        resetCmc(461),
        resetIom(961),
        muxOffline(978)
    }

CucsEquipmentIOCardIssues ::= TEXTUAL-CONVENTION
    STATUS        current
    DESCRIPTION
        ""
    SYNTAX        BITS {
        thermal(0),
        inoperable(1),
        voltage(2),
        perf(3),
        power(4),
        removed(5),
        fabricPortProblem(6),
        postFailure(7),
        serverPortProblem(8)
    }

CucsEquipmentIOCardStatsThresholded ::= TEXTUAL-CONVENTION
    STATUS        current
    DESCRIPTION
        ""
    SYNTAX        BITS {
        ambientTemp(0),
        ambientTempAvg(1),
        ambientTempMax(2),
        ambientTempMin(3),
        temp(4),
        tempAvg(5),
        tempMax(6),
        tempMin(7)
    }

CucsEquipmentIOCardStatsHistThresholded ::= TEXTUAL-CONVENTION
    STATUS        current
    DESCRIPTION
        ""
    SYNTAX        BITS {
        ambientTemp(0),
        ambientTempAvg(1),
        ambientTempMax(2),
        ambientTempMin(3),
        temp(4),
        tempAvg(5),
        tempMax(6),
        tempMin(7)
    }

CucsEquipmentInternalFanType ::= TEXTUAL-CONVENTION
    STATUS        current
    DESCRIPTION
        ""
    SYNTAX        INTEGER {
        chassis(0),
        switch(1),
        fex(2)
    }

CucsEquipmentLedColor ::= TEXTUAL-CONVENTION
    STATUS        current
    DESCRIPTION
        ""
    SYNTAX        INTEGER {
        unknown(0),
        green(1),
        amber(2),
        red(3),
        blue(4)
    }

CucsEquipmentLedLocatorState ::= TEXTUAL-CONVENTION
    STATUS        current
    DESCRIPTION
        ""
    SYNTAX        INTEGER {
        inactive(0),
        off(1),
        on(2)
    }

CucsEquipmentLedOperState ::= TEXTUAL-CONVENTION
    STATUS        current
    DESCRIPTION
        ""
    SYNTAX        INTEGER {
        unknown(0),
        on(1),
        off(2),
        blinking(3)
    }

CucsEquipmentLocatorLedFsmTaskItem ::= TEXTUAL-CONVENTION
    STATUS        current
    DESCRIPTION
        ""
    SYNTAX        INTEGER {
        nop(0),
        setLocatorLed(15),
        setFeLocatorLed(641)
    }

CucsEquipmentMemoryUnitDiscoveryModifierAction ::= TEXTUAL-CONVENTION
    STATUS        current
    DESCRIPTION
        ""
    SYNTAX        INTEGER {
        unknown(0),
        setRevToOne(1)
    }

CucsEquipmentMethod ::= TEXTUAL-CONVENTION
    STATUS        current
    DESCRIPTION
        ""
    SYNTAX        BITS {
        post(0),
        configCheck(1),
        diagCheck(2),
        selCheck(3)
    }

CucsEquipmentOperability ::= TEXTUAL-CONVENTION
    STATUS        current
    DESCRIPTION
        ""
    SYNTAX        INTEGER {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107)
    }

CucsEquipmentPOSTRecoverability ::= TEXTUAL-CONVENTION
    STATUS        current
    DESCRIPTION
        ""
    SYNTAX        INTEGER {
        unknown(0),
        recoverable(1),
        nonRecoverable(2)
    }

CucsEquipmentPictureType ::= TEXTUAL-CONVENTION
    STATUS        current
    DESCRIPTION
        ""
    SYNTAX        INTEGER {
        unknown(0),
        front(1),
        back(2),
        top(3),
        bottom(4),
        left(5),
        right(6)
    }

CucsEquipmentPowerState ::= TEXTUAL-CONVENTION
    STATUS        current
    DESCRIPTION
        ""
    SYNTAX        INTEGER {
        unknown(0),
        on(1),
        test(2),
        off(3),
        online(4),
        offline(5),
        offduty(6),
        degraded(7),
        powerSave(8),
        error(9),
        notSupported(100)
    }

CucsEquipmentPresence ::= TEXTUAL-CONVENTION
    STATUS        current
    DESCRIPTION
        ""
    SYNTAX        INTEGER {
        unknown(0),
        empty(1),
        equipped(10),
        missing(11),
        mismatch(12),
        equippedNotPrimary(13),
        equippedIdentityUnestablishable(20),
        mismatchIdentityUnestablishable(21),
        inaccessible(30),
        unauthorized(40),
        notSupported(100)
    }

CucsEquipmentPsuId ::= TEXTUAL-CONVENTION
    STATUS        current
    DESCRIPTION
        ""
    SYNTAX        Gauge32 (1..8)

CucsEquipmentPsuInputStatsThresholded ::= TEXTUAL-CONVENTION
    STATUS        current
    DESCRIPTION
        ""
    SYNTAX        BITS {
        current(0),
        currentAvg(1),
        currentMax(2),
        currentMin(3),
        power(4),
        powerAvg(5),
        powerMax(6),
        powerMin(7),
        voltage(8),
        voltageAvg(9),
        voltageMax(10),
        voltageMin(11)
    }

CucsEquipmentPsuInputStatsHistThresholded ::= TEXTUAL-CONVENTION
    STATUS        current
    DESCRIPTION
        ""
    SYNTAX        BITS {
        current(0),
        currentAvg(1),
        currentMax(2),
        currentMin(3),
        power(4),
        powerAvg(5),
        powerMax(6),
        powerMin(7),
        voltage(8),
        voltageAvg(9),
        voltageMax(10),
        voltageMin(11)
    }

CucsEquipmentPsuStatsThresholded ::= TEXTUAL-CONVENTION
    STATUS        current
    DESCRIPTION
        ""
    SYNTAX        BITS {
        ambientTemp(0),
        ambientTempAvg(1),
        ambientTempMax(2),
        ambientTempMin(3),
        input210v(4),
        input210vAvg(5),
        input210vMax(6),
        input210vMin(7),
        output12v(8),
        output12vAvg(9),
        output12vMax(10),
        output12vMin(11),
        output3v3(12),
        output3v3Avg(13),
        output3v3Max(14),
        output3v3Min(15),
        outputCurrent(16),
        outputCurrentAvg(17),
        outputCurrentMax(18),
        outputCurrentMin(19),
        outputPower(20),
        outputPowerAvg(21),
        outputPowerMax(22),
        outputPowerMin(23)
    }

CucsEquipmentPsuStatsHistThresholded ::= TEXTUAL-CONVENTION
    STATUS        current
    DESCRIPTION
        ""
    SYNTAX        BITS {
        ambientTemp(0),
        ambientTempAvg(1),
        ambientTempMax(2),
        ambientTempMin(3),
        input210v(4),
        input210vAvg(5),
        input210vMax(6),
        input210vMin(7),
        output12v(8),
        output12vAvg(9),
        output12vMax(10),
        output12vMin(11),
        output3v3(12),
        output3v3Avg(13),
        output3v3Max(14),
        output3v3Min(15),
        outputCurrent(16),
        outputCurrentAvg(17),
        outputCurrentMax(18),
        outputCurrentMin(19),
        outputPower(20),
        outputPowerAvg(21),
        outputPowerMax(22),
        outputPowerMin(23)
    }

CucsEquipmentRackUnitFanStatsThresholded ::= TEXTUAL-CONVENTION
    STATUS        current
    DESCRIPTION
        ""
    SYNTAX        BITS {
        speed(0),
        speedAvg(1),
        speedMax(2),
        speedMin(3)
    }

CucsEquipmentRackUnitFanStatsHistThresholded ::= TEXTUAL-CONVENTION
    STATUS        current
    DESCRIPTION
        ""
    SYNTAX        BITS {
        speed(0),
        speedAvg(1),
        speedMax(2),
        speedMin(3)
    }

CucsEquipmentRackUnitPsuStatsThresholded ::= TEXTUAL-CONVENTION
    STATUS        current
    DESCRIPTION
        ""
    SYNTAX        BITS {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CucsEquipmentRackUnitPsuStatsHistThresholded ::= TEXTUAL-CONVENTION
    STATUS        current
    DESCRIPTION
        ""
    SYNTAX        BITS {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CucsEquipmentRemovalConditions ::= TEXTUAL-CONVENTION
    STATUS        current
    DESCRIPTION
        ""
    SYNTAX        INTEGER {
        unknown(0),
        notApplicable(2),
        removableWhenOff(3),
        removableWhenOnOrOff(4)
    }

CucsEquipmentSensorThresholdStatus ::= TEXTUAL-CONVENTION
    STATUS        current
    DESCRIPTION
        ""
    SYNTAX        INTEGER {
        unknown(0),
        ok(1),
        upperNonRecoverable(2),
        upperCritical(3),
        upperNonCritical(4),
        lowerNonCritical(5),
        lowerCritical(6),
        lowerNonRecoverable(7),
        notSupported(100)
    }

CucsEquipmentSlotArrayLocation ::= TEXTUAL-CONVENTION
    STATUS        current
    DESCRIPTION
        ""
    SYNTAX        INTEGER {
        unknown(0),
        front(1),
        back(2),
        top(3),
        bottom(4),
        left(5),
        right(6)
    }

CucsEquipmentSlotArrayOrientation ::= TEXTUAL-CONVENTION
    STATUS        current
    DESCRIPTION
        ""
    SYNTAX        INTEGER {
        unknown(0),
        vertical(1),
        horizontal(2)
    }

CucsEquipmentSlotArraySelector ::= TEXTUAL-CONVENTION
    STATUS        current
    DESCRIPTION
        ""
    SYNTAX        INTEGER {
        unknown(0),
        psu(1),
        fan(2),
        iocard(3),
        diskSlot(5),
        driveSlot(6),
        usbPort(7),
        ethernetPort(8),
        comPort(9),
        parPort(10),
        vgaPort(11),
        dviPort(12),
        keyboardPort(13),
        mousePort(14)
    }

CucsEquipmentSlotSpanOrientation ::= TEXTUAL-CONVENTION
    STATUS        current
    DESCRIPTION
        ""
    SYNTAX        INTEGER {
        unknown(0),
        inline(1),
        transverse(2)
    }

CucsEquipmentSlotStatus ::= TEXTUAL-CONVENTION
    STATUS        current
    DESCRIPTION
        ""
    SYNTAX        INTEGER {
        unknown(0),
        empty(1),
        equipped(10),
        missing(11),
        mismatch(12),
        equippedNotPrimary(13),
        equippedIdentityUnestablishable(20),
        mismatchIdentityUnestablishable(21),
        inaccessible(30),
        unauthorized(40)
    }

CucsEquipmentXcvrId ::= TEXTUAL-CONVENTION
    STATUS        current
    DESCRIPTION
        ""
    SYNTAX        Gauge32 (1..40)

CucsEquipmentXcvrType ::= TEXTUAL-CONVENTION
    STATUS        current
    DESCRIPTION
        ""
    SYNTAX        INTEGER {
        unknown(0),
        h10gcu1m(1),
        h10gcu3m(2),
        h10gcu5m(3),
        h10gcu7m(4),
        h10gusr(5),
        h10glrmsm(6),
        cwdm1471(7),
        cwdm1531(8),
        cwdm1551(9),
        fet(10),
        sfp(11),
        x2(12),
        n10gbasesr(13),
        n10gbaselr(14),
        n10gbaselrm(15),
        n10gbaseer(16)
    }

CucsEquipmentFabricEpType ::= TEXTUAL-CONVENTION
    STATUS        current
    DESCRIPTION
        ""
    SYNTAX        INTEGER {
        unknown(0),
        chassis(1),
        fex(2),
        blade(3),
        rackUnit(4)
    }

CucsEtherErrStatsThresholded ::= TEXTUAL-CONVENTION
    STATUS        current
    DESCRIPTION
        ""
    SYNTAX        BITS {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CucsEtherErrStatsHistThresholded ::= TEXTUAL-CONVENTION
    STATUS        current
    DESCRIPTION
        ""
    SYNTAX        BITS {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CucsEtherLossStatsThresholded ::= TEXTUAL-CONVENTION
    STATUS        current
    DESCRIPTION
        ""
    SYNTAX        BITS {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CucsEtherLossStatsHistThresholded ::= TEXTUAL-CONVENTION
    STATUS        current
    DESCRIPTION
        ""
    SYNTAX        BITS {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CucsEtherPauseStatsThresholded ::= TEXTUAL-CONVENTION
    STATUS        current
    DESCRIPTION
        ""
    SYNTAX        BITS {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CucsEtherPauseStatsHistThresholded ::= TEXTUAL-CONVENTION
    STATUS        current
    DESCRIPTION
        ""
    SYNTAX        BITS {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CucsEtherRxStatsThresholded ::= TEXTUAL-CONVENTION
    STATUS        current
    DESCRIPTION
        ""
    SYNTAX        BITS {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherRxStatsHistThresholded ::= TEXTUAL-CONVENTION
    STATUS        current
    DESCRIPTION
        ""
    SYNTAX        BITS {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherSatelliteConnectionDisc ::= TEXTUAL-CONVENTION
    STATUS        current
    DESCRIPTION
        ""
    SYNTAX        INTEGER {
        absent(0),
        present(1),
        misConnect(2),
        missing(3),
        new(4)
    }

CucsEtherServerIntFIoIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsEtherServerIntFIoLocale ::= TEXTUAL-CONVENTION
    STATUS        current
    DESCRIPTION
        ""
    SYNTAX        BITS {
        server(0),
        chassis(1),
        internal(2),
        external(3)
    }

CucsEtherServerIntFIoTransport ::= TEXTUAL-CONVENTION
    STATUS        current
    DESCRIPTION
        ""
    SYNTAX        BITS {
        ether(0),
        dce(1),
        fc(2)
    }

CucsEtherServerIntFIoType ::= TEXTUAL-CONVENTION
    STATUS        current
    DESCRIPTION
        ""
    SYNTAX        BITS {
        lan(0),
        san(1),
        ipc(2)
    }

CucsEtherSwitchIntFIoAck ::= TEXTUAL-CONVENTION
    STATUS        current
    DESCRIPTION
        ""
    SYNTAX        INTEGER {
        unInitialized(0),
        unAcknowledged(1),
        unsupportedConnectivity(2),
        ok(3),
        removing(4),
        ackInProgress(6)
    }

CucsEtherSwitchIntFIoIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsEtherSwitchIntFIoLocale ::= TEXTUAL-CONVENTION
    STATUS        current
    DESCRIPTION
        ""
    SYNTAX        BITS {
        server(0),
        chassis(1),
        internal(2),
        external(3)
    }

CucsEtherSwitchIntFIoTransport ::= TEXTUAL-CONVENTION
    STATUS        current
    DESCRIPTION
        ""
    SYNTAX        BITS {
        ether(0),
        dce(1),
        fc(2)
    }

CucsEtherSwitchIntFIoType ::= TEXTUAL-CONVENTION
    STATUS        current
    DESCRIPTION
        ""
    SYNTAX        BITS {
        lan(0),
        san(1),
        ipc(2)
    }

CucsEtherTxStatsThresholded ::= TEXTUAL-CONVENTION
    STATUS        current
    DESCRIPTION
        ""
    SYNTAX        BITS {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEtherTxStatsHistThresholded ::= TEXTUAL-CONVENTION
    STATUS        current
    DESCRIPTION
        ""
    SYNTAX        BITS {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CucsEventEpCtrlLevel ::= TEXTUAL-CONVENTION
    STATUS        current
    DESCRIPTION
        ""
    SYNTAX        INTEGER {
        cleared(0),
        info(1),
        condition(2),
        warning(3),
        minor(4),
        major(5),
        critical(6)
    }

CucsExtmgmtArpTargetsMaxDeadlineTimeout ::= TEXTUAL-CONVENTION
    STATUS        current
    DESCRIPTION
        ""
    SYNTAX        Gauge32 (5..15)

CucsExtmgmtArpTargetsNumberOfArpRequests ::= TEXTUAL-CONVENTION
    STATUS        current
    DESCRIPTION
        ""
    SYNTAX        Gauge32 (1..5)

CucsExtmgmtGatewayPingMaxDeadlineTimeout ::= TEXTUAL-CONVENTION
    STATUS        current
    DESCRIPTION
        ""
    SYNTAX        Gauge32 (5..15)

CucsExtmgmtGatewayPingNumberOfPingRequests ::= TEXTUAL-CONVENTION
    STATUS        current
    DESCRIPTION
        ""
    SYNTAX        Gauge32 (1..5)

CucsExtmgmtIfMonPolicyAdminState ::= TEXTUAL-CONVENTION
    STATUS        current
    DESCRIPTION
        ""
    SYNTAX        INTEGER {
        enabled(1),
        disabled(2)
    }

CucsExtmgmtIfMonPolicyMonitorMechanism ::= TEXTUAL-CONVENTION
    STATUS        current
    DESCRIPTION
        ""
    SYNTAX        INTEGER {
        miiStatus(0),
        arpTargetPing(1),
        gatewayPing(2)
    }

CucsExtmgmtMiiStatusMaxRetryCount ::= TEXTUAL-CONVENTION
    STATUS        current
    DESCRIPTION
        ""
    SYNTAX        Gauge32 (1..3)

CucsExtmgmtMiiStatusRetryInterval ::= TEXTUAL-CONVENTION
    STATUS        current
    DESCRIPTION
        ""
    SYNTAX        Gauge32 (3..10)

CucsExtvmmKeyStoreFsmTaskItem ::= TEXTUAL-CONVENTION
    STATUS        current
    DESCRIPTION
        ""
    SYNTAX        INTEGER {
        nop(0),
        certInstall(539)
    }

CucsExtvmmMasterExtKeyFsmTaskItem ::= TEXTUAL-CONVENTION
    STATUS        current
    DESCRIPTION
        ""
    SYNTAX        INTEGER {
        nop(0),
        config(575)
    }

CucsExtvmmOwnership ::= TEXTUAL-CONVENTION
    STATUS        current
    DESCRIPTION
        ""
    SYNTAX        INTEGER {
        discovered(1),
        managed(2)
    }

CucsExtvmmProviderFsmTaskItem ::= TEXTUAL-CONVENTION
    STATUS        current
    DESCRIPTION
        ""
    SYNTAX        INTEGER {
        nop(0),
        config(536)
    }

CucsExtvmmSwitchDelTaskFsmTaskItem ::= TEXTUAL-CONVENTION
    STATUS        current
    DESCRIPTION
        ""
    SYNTAX        INTEGER {
        nop(0),
        removeProvider(542)
    }

CucsExtvmmVcVersion ::= TEXTUAL-CONVENTION
    STATUS        current
    DESCRIPTION
        ""
    SYNTAX        INTEGER {
        unknown(0),
        kl(1),
        klU1(2)
    }

CucsFabricADceSwSrvEpTransport ::= TEXTUAL-CONVENTION
    STATUS        current
    DESCRIPTION
        ""
    SYNTAX        BITS {
        ether(0),
        dce(1),
        fc(2)
    }

CucsFabricAEthEstcEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricAEthEstcEpTransport ::= TEXTUAL-CONVENTION
    STATUS        current
    DESCRIPTION
        ""
    SYNTAX        BITS {
        ether(0),
        dce(1),
        fc(2)
    }

CucsFabricAEthEstcEpType ::= TEXTUAL-CONVENTION
    STATUS        current
    DESCRIPTION
        ""
    SYNTAX        BITS {
        lan(0),
        san(1),
        ipc(2)
    }

CucsFabricAEthLanEpTransport ::= TEXTUAL-CONVENTION
    STATUS        current
    DESCRIPTION
        ""
    SYNTAX        BITS {
        ether(0),
        dce(1),
        fc(2)
    }

CucsFabricAFcEstcEpTransport ::= TEXTUAL-CONVENTION
    STATUS        current
    DESCRIPTION
        ""
    SYNTAX        BITS {
        ether(0),
        dce(1),
        fc(2)
    }

CucsFabricAFcEstcEpType ::= TEXTUAL-CONVENTION
    STATUS        current
    DESCRIPTION
        ""
    SYNTAX        BITS {
        lan(0),
        san(1),
        ipc(2)
    }

CucsFabricAFcSanEpTransport ::= TEXTUAL-CONVENTION
    STATUS        current
    DESCRIPTION
        ""
    SYNTAX        BITS {
        ether(0),
        dce(1),
        fc(2)
    }

CucsFabricAFcoeEstcEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricAFcoeEstcEpTransport ::= TEXTUAL-CONVENTION
    STATUS        current
    DESCRIPTION
        ""
    SYNTAX        BITS {
        ether(0),
        dce(1),
        fc(2)
    }

CucsFabricAFcoeEstcEpType ::= TEXTUAL-CONVENTION
    STATUS        current
    DESCRIPTION
        ""
    SYNTAX        BITS {
        lan(0),
        san(1),
        ipc(2)
    }

CucsFabricAVlanSharing ::= TEXTUAL-CONVENTION
    STATUS        current
    DESCRIPTION
        ""
    SYNTAX        INTEGER {
        none(0),
        primary(1),
        isolated(3)
    }

CucsFabricAVlanTransport ::= TEXTUAL-CONVENTION
    STATUS        current
    DESCRIPTION
        ""
    SYNTAX        BITS {
        ether(0),
        dce(1),
        fc(2)
    }

CucsFabricAVlanType ::= TEXTUAL-CONVENTION
    STATUS        current
    DESCRIPTION
        ""
    SYNTAX        BITS {
        lan(0),
        san(1),
        ipc(2)
    }

CucsFabricAVsanTransport ::= TEXTUAL-CONVENTION
    STATUS        current
    DESCRIPTION
        ""
    SYNTAX        BITS {
        ether(0),
        dce(1),
        fc(2)
    }

CucsFabricAVsanType ::= TEXTUAL-CONVENTION
    STATUS        current
    DESCRIPTION
        ""
    SYNTAX        BITS {
        lan(0),
        san(1),
        ipc(2)
    }

CucsFabricAdminState ::= TEXTUAL-CONVENTION
    STATUS        current
    DESCRIPTION
        ""
    SYNTAX        INTEGER {
        enabled(1),
        disabled(2)
    }

CucsFabricBHVlanSwitchId ::= TEXTUAL-CONVENTION
    STATUS        current
    DESCRIPTION
        ""
    SYNTAX        INTEGER {
        none(0),
        a(1),
        b(2),
        dual(3)
    }

CucsFabricBladeLifeCycle ::= TEXTUAL-CONVENTION
    STATUS        current
    DESCRIPTION
        ""
    SYNTAX        INTEGER {
        inService(1),
        outOfService(2),
        migrate(3)
    }

CucsFabricCIoEpIfType ::= TEXTUAL-CONVENTION
    STATUS        current
    DESCRIPTION
        ""
    SYNTAX        INTEGER {
        unknown(0),
        physical(1),
        aggregation(2),
        virtual(3)
    }

CucsFabricComputeEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricComputeEpType ::= TEXTUAL-CONVENTION
    STATUS        current
    DESCRIPTION
        ""
    SYNTAX        BITS {
        lan(0),
        san(1),
        ipc(2)
    }

CucsFabricComputeSlotEpSlotId ::= TEXTUAL-CONVENTION
    STATUS        current
    DESCRIPTION
        ""
    SYNTAX        Gauge32 (1..8)

CucsFabricComputeSlotEpFsmTaskItem ::= TEXTUAL-CONVENTION
    STATUS        current
    DESCRIPTION
        ""
    SYNTAX        INTEGER {
        nop(0),
        identify(20)
    }

CucsFabricConfigState ::= TEXTUAL-CONVENTION
    STATUS        current
    DESCRIPTION
        ""
    SYNTAX        INTEGER {
        applied(1),
        inconsistent(2)
    }

CucsFabricDceSwSrvEpPortId ::= TEXTUAL-CONVENTION
    STATUS        current
    DESCRIPTION
        ""
    SYNTAX        Gauge32 (1..40)

CucsFabricDceSwSrvEpSlotId ::= TEXTUAL-CONVENTION
    STATUS        current
    DESCRIPTION
        ""
    SYNTAX        Gauge32 (1..1)

CucsFabricDefaultZoningState ::= TEXTUAL-CONVENTION
    STATUS        current
    DESCRIPTION
        ""
    SYNTAX        INTEGER {
        disabled(0),
        enabled(1)
    }

CucsFabricEpVlanVlanType ::= TEXTUAL-CONVENTION
    STATUS        current
    DESCRIPTION
        ""
    SYNTAX        INTEGER {
        regular(0),
        default(1),
        native(2)
    }

CucsFabricEstcEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricEstcPcIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricEstcPcType ::= TEXTUAL-CONVENTION
    STATUS        current
    DESCRIPTION
        ""
    SYNTAX        BITS {
        lan(0),
        san(1),
        ipc(2)
    }

CucsFabricEthEstcTransport ::= TEXTUAL-CONVENTION
    STATUS        current
    DESCRIPTION
        ""
    SYNTAX        BITS {
        ether(0),
        dce(1),
        fc(2)
    }

CucsFabricEthEstcType ::= TEXTUAL-CONVENTION
    STATUS        current
    DESCRIPTION
        ""
    SYNTAX        BITS {
        lan(0),
        san(1),
        ipc(2)
    }

CucsFabricEthEstcEpPortId ::= TEXTUAL-CONVENTION
    STATUS        current
    DESCRIPTION
        ""
    SYNTAX        Gauge32 (1..40)

CucsFabricEthEstcEpSlotId ::= TEXTUAL-CONVENTION
    STATUS        current
    DESCRIPTION
        ""
    SYNTAX        Gauge32 (1..3)

CucsFabricEthEstcEpTransport ::= TEXTUAL-CONVENTION
    STATUS        current
    DESCRIPTION
        ""
    SYNTAX        BITS {
        ether(0),
        dce(1),
        fc(2)
    }

CucsFabricEthEstcEpType ::= TEXTUAL-CONVENTION
    STATUS        current
    DESCRIPTION
        ""
    SYNTAX        BITS {
        lan(0),
        san(1),
        ipc(2)
    }

CucsFabricEthEstcPcTransport ::= TEXTUAL-CONVENTION
    STATUS        current
    DESCRIPTION
        ""
    SYNTAX        BITS {
        ether(0),
        dce(1),
        fc(2)
    }

CucsFabricEthEstcPcEpPortId ::= TEXTUAL-CONVENTION
    STATUS        current
    DESCRIPTION
        ""
    SYNTAX        Gauge32 (1..40)

CucsFabricEthEstcPcEpSlotId ::= TEXTUAL-CONVENTION
    STATUS        current
    DESCRIPTION
        ""
    SYNTAX        Gauge32 (1..3)

CucsFabricEthEstcPortMode ::= TEXTUAL-CONVENTION
    STATUS        current
    DESCRIPTION
        ""
    SYNTAX        INTEGER {
        trunk(1),
        access(2)
    }

CucsFabricEthLanTransport ::= TEXTUAL-CONVENTION
    STATUS        current
    DESCRIPTION
        ""
    SYNTAX        BITS {
        ether(0),
        dce(1),
        fc(2)
    }

CucsFabricEthLanPcTransport ::= TEXTUAL-CONVENTION
    STATUS        current
    DESCRIPTION
        ""
    SYNTAX        BITS {
        ether(0),
        dce(1),
        fc(2)
    }

CucsFabricEthMonTransport ::= TEXTUAL-CONVENTION
    STATUS        current
    DESCRIPTION
        ""
    SYNTAX        BITS {
        ether(0),
        dce(1),
        fc(2)
    }

CucsFabricEthMonType ::= TEXTUAL-CONVENTION
    STATUS        current
    DESCRIPTION
        ""
    SYNTAX        BITS {
        lan(0),
        san(1),
        ipc(2)
    }

CucsFabricEthMonDestEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricEthMonDestEpPortId ::= TEXTUAL-CONVENTION
    STATUS        current
    DESCRIPTION
        ""
    SYNTAX        Gauge32 (1..40)

CucsFabricEthMonDestEpSlotId ::= TEXTUAL-CONVENTION
    STATUS        current
    DESCRIPTION
        ""
    SYNTAX        Gauge32 (1..3)

CucsFabricEthMonDestEpType ::= TEXTUAL-CONVENTION
    STATUS        current
    DESCRIPTION
        ""
    SYNTAX        BITS {
        lan(0),
        san(1),
        ipc(2)
    }

CucsFabricEthMonFiltEpType ::= TEXTUAL-CONVENTION
    STATUS        current
    DESCRIPTION
        ""
    SYNTAX        BITS {
        lan(0),
        san(1),
        ipc(2)
    }

CucsFabricEthMonFiltRefType ::= TEXTUAL-CONVENTION
    STATUS        current
    DESCRIPTION
        ""
    SYNTAX        BITS {
        lan(0),
        san(1),
        ipc(2)
    }

CucsFabricEthMonLanTransport ::= TEXTUAL-CONVENTION
    STATUS        current
    DESCRIPTION
        ""
    SYNTAX        BITS {
        ether(0),
        dce(1),
        fc(2)
    }

CucsFabricEthMonLanType ::= TEXTUAL-CONVENTION
    STATUS        current
    DESCRIPTION
        ""
    SYNTAX        BITS {
        lan(0),
        san(1),
        ipc(2)
    }

CucsFabricEthMonSrcEpType ::= TEXTUAL-CONVENTION
    STATUS        current
    DESCRIPTION
        ""
    SYNTAX        BITS {
        lan(0),
        san(1),
        ipc(2)
    }

CucsFabricEthMonSrcRefType ::= TEXTUAL-CONVENTION
    STATUS        current
    DESCRIPTION
        ""
    SYNTAX        BITS {
        lan(0),
        san(1),
        ipc(2)
    }

CucsFabricEthSourceType ::= TEXTUAL-CONVENTION
    STATUS        current
    DESCRIPTION
        ""
    SYNTAX        INTEGER {
        vnic(1),
        uplinkPort(2),
        vlan(3),
        serverPort(4),
        portChannel(5),
        hostPort(6),
        storage(7),
        nasPort(8),
        vhba(20)
    }

CucsFabricEthTargetEpTransport ::= TEXTUAL-CONVENTION
    STATUS        current
    DESCRIPTION
        ""
    SYNTAX        BITS {
        ether(0),
        dce(1),
        fc(2)
    }

CucsFabricEthVlanPcTransport ::= TEXTUAL-CONVENTION
    STATUS        current
    DESCRIPTION
        ""
    SYNTAX        BITS {
        ether(0),
        dce(1),
        fc(2)
    }

CucsFabricExternalLocale ::= TEXTUAL-CONVENTION
    STATUS        current
    DESCRIPTION
        ""
    SYNTAX        BITS {
        server(0),
        chassis(1),
        internal(2),
        external(3)
    }

CucsFabricExternalEpAdminState ::= TEXTUAL-CONVENTION
    STATUS        current
    DESCRIPTION
        ""
    SYNTAX        INTEGER {
        enabled(1),
        disabled(2)
    }

CucsFabricExternalEpLocale ::= TEXTUAL-CONVENTION
    STATUS        current
    DESCRIPTION
        ""
    SYNTAX        BITS {
        server(0),
        chassis(1),
        internal(2),
        external(3)
    }

CucsFabricExternalPcLocale ::= TEXTUAL-CONVENTION
    STATUS        current
    DESCRIPTION
        ""
    SYNTAX        BITS {
        server(0),
        chassis(1),
        internal(2),
        external(3)
    }

CucsFabricFcEstcTransport ::= TEXTUAL-CONVENTION
    STATUS        current
    DESCRIPTION
        ""
    SYNTAX        BITS {
        ether(0),
        dce(1),
        fc(2)
    }

CucsFabricFcEstcType ::= TEXTUAL-CONVENTION
    STATUS        current
    DESCRIPTION
        ""
    SYNTAX        BITS {
        lan(0),
        san(1),
        ipc(2)
    }

CucsFabricFcEstcEpPortId ::= TEXTUAL-CONVENTION
    STATUS        current
    DESCRIPTION
        ""
    SYNTAX        Gauge32 (1..40)

CucsFabricFcEstcEpSlotId ::= TEXTUAL-CONVENTION
    STATUS        current
    DESCRIPTION
        ""
    SYNTAX        Gauge32 (2..5)

CucsFabricFcMonTransport ::= TEXTUAL-CONVENTION
    STATUS        current
    DESCRIPTION
        ""
    SYNTAX        BITS {
        ether(0),
        dce(1),
        fc(2)
    }

CucsFabricFcMonType ::= TEXTUAL-CONVENTION
    STATUS        current
    DESCRIPTION
        ""
    SYNTAX        BITS {
        lan(0),
        san(1),
        ipc(2)
    }

CucsFabricFcMonDestEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricFcMonDestEpPortId ::= TEXTUAL-CONVENTION
    STATUS        current
    DESCRIPTION
        ""
    SYNTAX        Gauge32 (1..40)

CucsFabricFcMonDestEpSlotId ::= TEXTUAL-CONVENTION
    STATUS        current
    DESCRIPTION
        ""
    SYNTAX        Gauge32 (2..5)

CucsFabricFcMonDestEpType ::= TEXTUAL-CONVENTION
    STATUS        current
    DESCRIPTION
        ""
    SYNTAX        BITS {
        lan(0),
        san(1),
        ipc(2)
    }

CucsFabricFcMonFiltEpType ::= TEXTUAL-CONVENTION
    STATUS        current
    DESCRIPTION
        ""
    SYNTAX        BITS {
        lan(0),
        san(1),
        ipc(2)
    }

CucsFabricFcMonFiltRefType ::= TEXTUAL-CONVENTION
    STATUS        current
    DESCRIPTION
        ""
    SYNTAX        BITS {
        lan(0),
        san(1),
        ipc(2)
    }

CucsFabricFcMonSanTransport ::= TEXTUAL-CONVENTION
    STATUS        current
    DESCRIPTION
        ""
    SYNTAX        BITS {
        ether(0),
        dce(1),
        fc(2)
    }

CucsFabricFcMonSanType ::= TEXTUAL-CONVENTION
    STATUS        current
    DESCRIPTION
        ""
    SYNTAX        BITS {
        lan(0),
        san(1),
        ipc(2)
    }

CucsFabricFcMonSrcEpType ::= TEXTUAL-CONVENTION
    STATUS        current
    DESCRIPTION
        ""
    SYNTAX        BITS {
        lan(0),
        san(1),
        ipc(2)
    }

CucsFabricFcMonSrcRefType ::= TEXTUAL-CONVENTION
    STATUS        current
    DESCRIPTION
        ""
    SYNTAX        BITS {
        lan(0),
        san(1),
        ipc(2)
    }

CucsFabricFcSanTransport ::= TEXTUAL-CONVENTION
    STATUS        current
    DESCRIPTION
        ""
    SYNTAX        BITS {
        ether(0),
        dce(1),
        fc(2)
    }

CucsFabricFcSanEpPortId ::= TEXTUAL-CONVENTION
    STATUS        current
    DESCRIPTION
        ""
    SYNTAX        Gauge32 (1..40)

CucsFabricFcSanEpSlotId ::= TEXTUAL-CONVENTION
    STATUS        current
    DESCRIPTION
        ""
    SYNTAX        Gauge32 (2..5)

CucsFabricFcSanPcTransport ::= TEXTUAL-CONVENTION
    STATUS        current
    DESCRIPTION
        ""
    SYNTAX        BITS {
        ether(0),
        dce(1),
        fc(2)
    }

CucsFabricFcSanPcEpPortId ::= TEXTUAL-CONVENTION
    STATUS        current
    DESCRIPTION
        ""
    SYNTAX        Gauge32 (1..40)

CucsFabricFcSanPcEpSlotId ::= TEXTUAL-CONVENTION
    STATUS        current
    DESCRIPTION
        ""
    SYNTAX        Gauge32 (2..5)

CucsFabricFcSourceType ::= TEXTUAL-CONVENTION
    STATUS        current
    DESCRIPTION
        ""
    SYNTAX        INTEGER {
        vhba(1),
        uplinkPort(2),
        vsan(3),
        storage(4),
        portChannel(5)
    }

CucsFabricFcVsanPcTransport ::= TEXTUAL-CONVENTION
    STATUS        current
    DESCRIPTION
        ""
    SYNTAX        BITS {
        ether(0),
        dce(1),
        fc(2)
    }

CucsFabricFcVsanPortEpPortId ::= TEXTUAL-CONVENTION
    STATUS        current
    DESCRIPTION
        ""
    SYNTAX        Gauge32 (1..256)

CucsFabricFcVsanPortEpSlotId ::= TEXTUAL-CONVENTION
    STATUS        current
    DESCRIPTION
        ""
    SYNTAX        Gauge32 (0..5)

CucsFabricFcoeEstcEpPortId ::= TEXTUAL-CONVENTION
    STATUS        current
    DESCRIPTION
        ""
    SYNTAX        Gauge32 (1..40)

CucsFabricFcoeEstcEpSlotId ::= TEXTUAL-CONVENTION
    STATUS        current
    DESCRIPTION
        ""
    SYNTAX        Gauge32 (1..3)

CucsFabricFcoeVsanPortEpPortId ::= TEXTUAL-CONVENTION
    STATUS        current
    DESCRIPTION
        ""
    SYNTAX        Gauge32 (1..256)

CucsFabricFcoeVsanPortEpSlotId ::= TEXTUAL-CONVENTION
    STATUS        current
    DESCRIPTION
        ""
    SYNTAX        Gauge32 (1..5)

CucsFabricInternalLocale ::= TEXTUAL-CONVENTION
    STATUS        current
    DESCRIPTION
        ""
    SYNTAX        BITS {
        server(0),
        chassis(1),
        internal(2),
        external(3)
    }

CucsFabricInternalDceSrvTransport ::= TEXTUAL-CONVENTION
    STATUS        current
    DESCRIPTION
        ""
    SYNTAX        BITS {
        ether(0),
        dce(1),
        fc(2)
    }

CucsFabricInternalDceSrvType ::= TEXTUAL-CONVENTION
    STATUS        current
    DESCRIPTION
        ""
    SYNTAX        BITS {
        lan(0),
        san(1),
        ipc(2)
    }

CucsFabricInternalEpAdminState ::= TEXTUAL-CONVENTION
    STATUS        current
    DESCRIPTION
        ""
    SYNTAX        INTEGER {
        enabled(1),
        disabled(2)
    }

CucsFabricInternalEpLocale ::= TEXTUAL-CONVENTION
    STATUS        current
    DESCRIPTION
        ""
    SYNTAX        BITS {
        server(0),
        chassis(1),
        internal(2),
        external(3)
    }

CucsFabricLanType ::= TEXTUAL-CONVENTION
    STATUS        current
    DESCRIPTION
        ""
    SYNTAX        BITS {
        lan(0),
        san(1),
        ipc(2)
    }

CucsFabricLanCloudFsmTaskItem ::= TEXTUAL-CONVENTION
    STATUS        current
    DESCRIPTION
        ""
    SYNTAX        INTEGER {
        nop(0),
        switchMode(184)
    }

CucsFabricLanEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricLanEpType ::= TEXTUAL-CONVENTION
    STATUS        current
    DESCRIPTION
        ""
    SYNTAX        BITS {
        lan(0),
        san(1),
        ipc(2)
    }

CucsFabricLanPcIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricLanPcType ::= TEXTUAL-CONVENTION
    STATUS        current
    DESCRIPTION
        ""
    SYNTAX        BITS {
        lan(0),
        san(1),
        ipc(2)
    }

CucsFabricLifeCycle ::= TEXTUAL-CONVENTION
    STATUS        current
    DESCRIPTION
        ""
    SYNTAX        INTEGER {
        inService(1),
        outOfService(2)
    }

CucsFabricMembershipStatus ::= TEXTUAL-CONVENTION
    STATUS        current
    DESCRIPTION
        ""
    SYNTAX        INTEGER {
        down(1),
        up(2),
        hotStandby(3),
        suspended(4),
        individual(5),
        moduleRemoved(6),
        incompatibleSpeed(7),
        unknown(8)
    }

CucsFabricMonAdminState ::= TEXTUAL-CONVENTION
    STATUS        current
    DESCRIPTION
        ""
    SYNTAX        INTEGER {
        enabled(1),
        disabled(2)
    }

CucsFabricMonOperState ::= TEXTUAL-CONVENTION
    STATUS        current
    DESCRIPTION
        ""
    SYNTAX        INTEGER {
        unknown(0),
        up(1),
        down(2),
        error(3)
    }

CucsFabricMonOperStateReason ::= TEXTUAL-CONVENTION
    STATUS        current
    DESCRIPTION
        ""
    SYNTAX        INTEGER {
        active(0),
        noHardwareResource(1),
        noOperationalSrcDst(2),
        genericError(3),
        noSourcesConfigured(4),
        noDestinationConfigured(5),
        noSourceDestinationConfigured(6),
        sessionAdminShut(7),
        wrongDestinationMode(8),
        wrongSourceMode(9),
        tunnelMisconfDown(10),
        noFlowIdSpecified(11),
        unknown(12)
    }

CucsFabricPIoEpIfType ::= TEXTUAL-CONVENTION
    STATUS        current
    DESCRIPTION
        ""
    SYNTAX        INTEGER {
        unknown(0),
        physical(1),
        aggregation(2),
        virtual(3)
    }

CucsFabricPIoEpPortId ::= TEXTUAL-CONVENTION
    STATUS        current
    DESCRIPTION
        ""
    SYNTAX        Gauge32 (1..40)

CucsFabricPIoEpSlotId ::= TEXTUAL-CONVENTION
    STATUS        current
    DESCRIPTION
        ""
    SYNTAX        Gauge32 (1..3)

CucsFabricPathEpIfType ::= TEXTUAL-CONVENTION
    STATUS        current
    DESCRIPTION
        ""
    SYNTAX        INTEGER {
        unknown(0),
        physical(1),
        aggregation(2),
        virtual(3)
    }

CucsFabricPathEpLocale ::= TEXTUAL-CONVENTION
    STATUS        current
    DESCRIPTION
        ""
    SYNTAX        BITS {
        server(0),
        chassis(1),
        internal(2),
        external(3)
    }

CucsFabricPcConfigStatus ::= TEXTUAL-CONVENTION
    STATUS        current
    DESCRIPTION
        ""
    SYNTAX        INTEGER {
        applied(1),
        incompatibleSpeed(2)
    }

CucsFabricSanType ::= TEXTUAL-CONVENTION
    STATUS        current
    DESCRIPTION
        ""
    SYNTAX        BITS {
        lan(0),
        san(1),
        ipc(2)
    }

CucsFabricSanCloudFsmTaskItem ::= TEXTUAL-CONVENTION
    STATUS        current
    DESCRIPTION
        ""
    SYNTAX        INTEGER {
        nop(0),
        switchMode(875)
    }

CucsFabricSanEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricSanEpType ::= TEXTUAL-CONVENTION
    STATUS        current
    DESCRIPTION
        ""
    SYNTAX        BITS {
        lan(0),
        san(1),
        ipc(2)
    }

CucsFabricSanPcIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricSanPcType ::= TEXTUAL-CONVENTION
    STATUS        current
    DESCRIPTION
        ""
    SYNTAX        BITS {
        lan(0),
        san(1),
        ipc(2)
    }

CucsFabricSlotAdminState ::= TEXTUAL-CONVENTION
    STATUS        current
    DESCRIPTION
        ""
    SYNTAX        INTEGER {
        acknowledged(1),
        reacknowledge(3)
    }

CucsFabricSwChEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricSwChEpType ::= TEXTUAL-CONVENTION
    STATUS        current
    DESCRIPTION
        ""
    SYNTAX        BITS {
        lan(0),
        san(1),
        ipc(2)
    }

CucsFabricSwSrvEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricSwSrvEpType ::= TEXTUAL-CONVENTION
    STATUS        current
    DESCRIPTION
        ""
    SYNTAX        BITS {
        lan(0),
        san(1),
        ipc(2)
    }

CucsFabricSwitchingMode ::= TEXTUAL-CONVENTION
    STATUS        current
    DESCRIPTION
        ""
    SYNTAX        INTEGER {
        endHost(0),
        switch(1)
    }

CucsFabricTargetEpType ::= TEXTUAL-CONVENTION
    STATUS        current
    DESCRIPTION
        ""
    SYNTAX        BITS {
        lan(0),
        san(1),
        ipc(2)
    }

CucsFabricTrafficDirection ::= TEXTUAL-CONVENTION
    STATUS        current
    DESCRIPTION
        ""
    SYNTAX        INTEGER {
        rx(1),
        tx(2),
        both(3)
    }

CucsFabricVConPlacementPref ::= TEXTUAL-CONVENTION
    STATUS        current
    DESCRIPTION
        ""
    SYNTAX        INTEGER {
        physical(1),
        auto(2)
    }

CucsFabricVConSelectPref ::= TEXTUAL-CONVENTION
    STATUS        current
    DESCRIPTION
        ""
    SYNTAX        INTEGER {
        assignedOnly(1),
        unassignedOnly(2),
        excludeDynamic(3),
        dynamicOnly(4),
        excludeUnassigned(5),
        all(7)
    }

CucsFabricVConSharePref ::= TEXTUAL-CONVENTION
    STATUS        current
    DESCRIPTION
        ""
    SYNTAX        INTEGER {
        exclusiveOnly(1),
        exclusivePreferred(2),
        sameTransport(3),
        differentTransport(4),
        shared(5)
    }

CucsFabricVConTransportPref ::= TEXTUAL-CONVENTION
    STATUS        current
    DESCRIPTION
        ""
    SYNTAX        BITS {
        fc(0),
        ethernet(1)
    }

CucsFabricVlanSwitchId ::= TEXTUAL-CONVENTION
    STATUS        current
    DESCRIPTION
        ""
    SYNTAX        INTEGER {
        none(0),
        a(1),
        b(2),
        dual(3)
    }

CucsFabricVnetEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsFabricVnetEpLocale ::= TEXTUAL-CONVENTION
    STATUS        current
    DESCRIPTION
        ""
    SYNTAX        BITS {
        server(0),
        chassis(1),
        internal(2),
        external(3)
    }

CucsFabricVsanSwitchId ::= TEXTUAL-CONVENTION
    STATUS        current
    DESCRIPTION
        ""
    SYNTAX        INTEGER {
        none(0),
        a(1),
        b(2),
        dual(3)
    }

CucsFaultPolicyClearAction ::= TEXTUAL-CONVENTION
    STATUS        current
    DESCRIPTION
        ""
    SYNTAX        INTEGER {
        retain(0),
        delete(1)
    }

CucsFcErrStatsThresholded ::= TEXTUAL-CONVENTION
    STATUS        current
    DESCRIPTION
        ""
    SYNTAX        BITS {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CucsFcErrStatsHistThresholded ::= TEXTUAL-CONVENTION
    STATUS        current
    DESCRIPTION
        ""
    SYNTAX        BITS {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CucsFcStatsThresholded ::= TEXTUAL-CONVENTION
    STATUS        current
    DESCRIPTION
        ""
    SYNTAX        BITS {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CucsFcStatsHistThresholded ::= TEXTUAL-CONVENTION
    STATUS        current
    DESCRIPTION
        ""
    SYNTAX        BITS {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CucsFcpoolBootTargetType ::= TEXTUAL-CONVENTION
    STATUS        current
    DESCRIPTION
        ""
    SYNTAX        INTEGER {
        primary(0),
        secondary(1)
    }

CucsFcpoolInitiatorsPurpose ::= TEXTUAL-CONVENTION
    STATUS        current
    DESCRIPTION
        ""
    SYNTAX        INTEGER {
        portWwnAssignment(1),
        nodeWwnAssignment(2)
    }

CucsFirmwareAdminState ::= TEXTUAL-CONVENTION
    STATUS        current
    DESCRIPTION
        ""
    SYNTAX        INTEGER {
        active(0),
        deleted(1)
    }

CucsFirmwareBootUnitImage ::= TEXTUAL-CONVENTION
    STATUS        current
    DESCRIPTION
        ""
    SYNTAX        INTEGER {
        running(0),
        backup(1)
    }

CucsFirmwareCompleteness ::= TEXTUAL-CONVENTION
    STATUS        current
    DESCRIPTION
        ""
    SYNTAX        INTEGER {
        partial(0),
        complete(1)
    }

CucsFirmwareComponentType ::= TEXTUAL-CONVENTION
    STATUS        current
    DESCRIPTION
        ""
    SYNTAX        BITS {
        kernel(0),
        system(1),
        combined(2),
        bootLoader(3)
    }

CucsFirmwareDependencyRelationship ::= TEXTUAL-CONVENTION
    STATUS        current
    DESCRIPTION
        ""
    SYNTAX        INTEGER {
        special(0),
        ancestor(1),
        descendent(2)
    }

CucsFirmwareDependencyScope ::= TEXTUAL-CONVENTION
    STATUS        current
    DESCRIPTION
        ""
    SYNTAX        INTEGER {
        unknown(0),
        blade(1),
        chassis(2),
        system(4),
        switch(8),
        global(16)
    }

CucsFirmwareDependencySensitivity ::= TEXTUAL-CONVENTION
    STATUS        current
    DESCRIPTION
        ""
    SYNTAX        INTEGER {
        global(0),
        fabric(1),
        path(2)
    }

CucsFirmwareDistributableFsmTaskItem ::= TEXTUAL-CONVENTION
    STATUS        current
    DESCRIPTION
        ""
    SYNTAX        INTEGER {
        nop(0),
        delete(594)
    }

CucsFirmwareDistributableType ::= TEXTUAL-CONVENTION
    STATUS        current
    DESCRIPTION
        ""
    SYNTAX        INTEGER {
        unknown(0),
        image(1),
        fullBundle(2),
        infrastructureBundle(3),
        bSeriesBundle(4),
        cSeriesBundle(5)
    }

CucsFirmwareDownloadActivity ::= TEXTUAL-CONVENTION
    STATUS        current
    DESCRIPTION
        ""
    SYNTAX        INTEGER {
        restart(0),
        idle(1)
    }

CucsFirmwareDownloaderFsmTaskItem ::= TEXTUAL-CONVENTION
    STATUS        current
    DESCRIPTION
        ""
    SYNTAX        INTEGER {
        nop(0),
        download(233)
    }

CucsFirmwareImageDeleted ::= TEXTUAL-CONVENTION
    STATUS        current
    DESCRIPTION
        ""
    SYNTAX        BITS {
        a(0),
        b(1)
    }

CucsFirmwareImageError ::= TEXTUAL-CONVENTION
    STATUS        current
    DESCRIPTION
        ""
    SYNTAX        INTEGER {
        none(0),
        checksumFailure(1),
        filesystemError(2),
        mgmtConnectError(3),
        bootConfMissing(4),
        crcFailure(5),
        unknownError(6)
    }

CucsFirmwareImageFsmTaskItem ::= TEXTUAL-CONVENTION
    STATUS        current
    DESCRIPTION
        ""
    SYNTAX        INTEGER {
        nop(0),
        delete(240)
    }

CucsFirmwareImagePresence ::= TEXTUAL-CONVENTION
    STATUS        current
    DESCRIPTION
        ""
    SYNTAX        BITS {
        a(0),
        b(1)
    }

CucsFirmwareImageState ::= TEXTUAL-CONVENTION
    STATUS        current
    DESCRIPTION
        ""
    SYNTAX        INTEGER {
        ready(0),
        scheduled(1),
        updating(2),
        activating(3),
        failed(4),
        setStartup(5),
        rebooting(6),
        pendingNextBoot(7),
        throttled(8),
        badImage(11)
    }

CucsFirmwareItemType ::= TEXTUAL-CONVENTION
    STATUS        current
    DESCRIPTION
        ""
    SYNTAX        INTEGER {
        unspecified(0),
        bladeController(4),
        bladeBios(6),
        adaptor(7),
        storageController(8),
        hostNic(9),
        hostHba(10),
        hostHbaOptionrom(11),
        hostNicOptionrom(12),
        boardController(13),
        localDisk(14)
    }

CucsFirmwarePackMode ::= TEXTUAL-CONVENTION
    STATUS        current
    DESCRIPTION
        ""
    SYNTAX        INTEGER {
        staged(0),
        oneShot(1)
    }

CucsFirmwarePackItemPresence ::= TEXTUAL-CONVENTION
    STATUS        current
    DESCRIPTION
        ""
    SYNTAX        INTEGER {
        unknown(0),
        missing(1),
        present(2)
    }

CucsFirmwareRunningDeployment ::= TEXTUAL-CONVENTION
    STATUS        current
    DESCRIPTION
        ""
    SYNTAX        INTEGER {
        unspecified(0),
        kernel(1),
        bootLoader(2),
        system(3)
    }

CucsFirmwareTransferState ::= TEXTUAL-CONVENTION
    STATUS        current
    DESCRIPTION
        ""
    SYNTAX        INTEGER {
        init(0),
        downloading(1),
        downloaded(2),
        failed(3)
    }

CucsFirmwareTransport ::= TEXTUAL-CONVENTION
    STATUS        current
    DESCRIPTION
        ""
    SYNTAX        INTEGER {
        ftp(0),
        tftp(1),
        scp(2),
        sftp(3),
        local(4)
    }

CucsFirmwareTriggerState ::= TEXTUAL-CONVENTION
    STATUS        current
    DESCRIPTION
        ""
    SYNTAX        INTEGER {
        triggered(0),
        trigger(1)
    }

CucsFirmwareType ::= TEXTUAL-CONVENTION
    STATUS        current
    DESCRIPTION
        ""
    SYNTAX        INTEGER {
        unspecified(0),
        switchKernel(1),
        switchSoftware(2),
        system(3),
        bladeController(4),
        iocard(5),
        fex(6),
        adaptor(7),
        storageController(8),
        hostNic(9),
        hostHba(10),
        hostHbaOptionrom(11),
        hostNicOptionrom(12),
        boardController(13),
        localDisk(14),
        diag(15),
        catalog(16),
        mgmtExt(17),
        debugPlugIn(18)
    }

CucsFirmwareUpdatableDeployment ::= TEXTUAL-CONVENTION
    STATUS        current
    DESCRIPTION
        ""
    SYNTAX        INTEGER {
        unspecified(0),
        backup(4)
    }

CucsFlowctrlFlowControl ::= TEXTUAL-CONVENTION
    STATUS        current
    DESCRIPTION
        ""
    SYNTAX        INTEGER {
        off(0),
        on(1)
    }

CucsFlowctrlPriorityPause ::= TEXTUAL-CONVENTION
    STATUS        current
    DESCRIPTION
        ""
    SYNTAX        INTEGER {
        auto(0),
        on(1)
    }

CucsFsmCompletion ::= TEXTUAL-CONVENTION
    STATUS        current
    DESCRIPTION
        ""
    SYNTAX        INTEGER {
        scheduled(0),
        processing(1),
        completed(2),
        cancelled(3)
    }

CucsFsmFlags ::= TEXTUAL-CONVENTION
    STATUS        current
    DESCRIPTION
        ""
    SYNTAX        BITS {
        unused(1)
    }

CucsFsmLifecycle ::= TEXTUAL-CONVENTION
    STATUS        current
    DESCRIPTION
        ""
    SYNTAX        INTEGER {
        available(0),
        allocated(1),
        deallocated(2),
        repurposed(3)
    }

CucsHostagAction ::= TEXTUAL-CONVENTION
    STATUS        current
    DESCRIPTION
        ""
    SYNTAX        INTEGER {
        none(0)
    }

CucsHostagAgentType ::= TEXTUAL-CONVENTION
    STATUS        current
    DESCRIPTION
        ""
    SYNTAX        INTEGER {
        indeterminate(0),
        pnuosAgent(1),
        hostAgent(2)
    }

CucsHostagEvent ::= TEXTUAL-CONVENTION
    STATUS        current
    DESCRIPTION
        ""
    SYNTAX        INTEGER {
        none(0)
    }

CucsHostimgComposition ::= TEXTUAL-CONVENTION
    STATUS        current
    DESCRIPTION
        ""
    SYNTAX        INTEGER {
        complete(0),
        componentized(1)
    }

CucsHostimgDistribution ::= TEXTUAL-CONVENTION
    STATUS        current
    DESCRIPTION
        ""
    SYNTAX        INTEGER {
        unknown(0),
        fedora(1)
    }

CucsHostimgImgType ::= TEXTUAL-CONVENTION
    STATUS        current
    DESCRIPTION
        ""
    SYNTAX        INTEGER {
        unknown(0),
        esxi(1),
        kvm(2),
        xen(3),
        linux(4),
        windows(5),
        gpxeScript(6)
    }

CucsHostimgType ::= TEXTUAL-CONVENTION
    STATUS        current
    DESCRIPTION
        ""
    SYNTAX        INTEGER {
        complete(0),
        kernel(1),
        fileSystem(2),
        module(3),
        gpxeScript(4)
    }

CucsImgsecKeyType ::= TEXTUAL-CONVENTION
    STATUS        current
    DESCRIPTION
        ""
    SYNTAX        INTEGER {
        public(0),
        private(1),
        shared(2)
    }

CucsIpProtocol ::= TEXTUAL-CONVENTION
    STATUS        current
    DESCRIPTION
        ""
    SYNTAX        INTEGER {
        tcp(1),
        udp(2)
    }

CucsLicenseDownloadActivity ::= TEXTUAL-CONVENTION
    STATUS        current
    DESCRIPTION
        ""
    SYNTAX        INTEGER {
        restart(0),
        idle(1)
    }

CucsLicenseDownloaderFsmTaskItem ::= TEXTUAL-CONVENTION
    STATUS        current
    DESCRIPTION
        ""
    SYNTAX        INTEGER {
        nop(0),
        download(853)
    }

CucsLicenseFeatureType ::= TEXTUAL-CONVENTION
    STATUS        current
    DESCRIPTION
        ""
    SYNTAX        INTEGER {
        counted(0),
        boolean(1)
    }

CucsLicenseFileFsmTaskItem ::= TEXTUAL-CONVENTION
    STATUS        current
    DESCRIPTION
        ""
    SYNTAX        INTEGER {
        nop(0),
        install(858),
        clear(861)
    }

CucsLicenseFileState ::= TEXTUAL-CONVENTION
    STATUS        current
    DESCRIPTION
        ""
    SYNTAX        INTEGER {
        unknown(0),
        installPending(1),
        installing(2),
        stale(3),
        installed(4),
        installFailed(5),
        deletePending(6),
        deleting(7),
        deleted(8),
        deleteFailed(9),
        validated(10)
    }

CucsLicenseInstanceFsmTaskItem ::= TEXTUAL-CONVENTION
    STATUS        current
    DESCRIPTION
        ""
    SYNTAX        INTEGER {
        nop(0),
        updateFlexlm(864)
    }

CucsLicensePeerStatus ::= TEXTUAL-CONVENTION
    STATUS        current
    DESCRIPTION
        ""
    SYNTAX        INTEGER {
        noPeer(0),
        unknown(1),
        lacks(2),
        matching(3)
    }

CucsLicenseScope ::= TEXTUAL-CONVENTION
    STATUS        current
    DESCRIPTION
        ""
    SYNTAX        INTEGER {
        a(1),
        b(2),
        server(3),
        unknown(4)
    }

CucsLicenseState ::= TEXTUAL-CONVENTION
    STATUS        current
    DESCRIPTION
        ""
    SYNTAX        INTEGER {
        unknown(0),
        licenseOk(1),
        licenseInsufficient(2),
        licenseGraceperiod(3),
        licenseExpired(4),
        licenseNotLicensed(5)
    }

CucsLicenseTransferState ::= TEXTUAL-CONVENTION
    STATUS        current
    DESCRIPTION
        ""
    SYNTAX        INTEGER {
        init(0),
        downloading(1),
        downloaded(2),
        failed(3)
    }

CucsLicenseTransport ::= TEXTUAL-CONVENTION
    STATUS        current
    DESCRIPTION
        ""
    SYNTAX        INTEGER {
        ftp(0),
        tftp(1),
        scp(2),
        sftp(3),
        local(4)
    }

CucsLicenseType ::= TEXTUAL-CONVENTION
    STATUS        current
    DESCRIPTION
        ""
    SYNTAX        INTEGER {
        increment(0),
        upgrade(1),
        feature(2)
    }

CucsLsAgentCapability ::= TEXTUAL-CONVENTION
    STATUS        current
    DESCRIPTION
        ""
    SYNTAX        INTEGER {
        l2IfConfig(1),
        l3IfConfig(2),
        hostNameConfig(4),
        stats(8),
        states(16)
    }

CucsLsAgentMode ::= TEXTUAL-CONVENTION
    STATUS        current
    DESCRIPTION
        ""
    SYNTAX        INTEGER {
        noAgent(1),
        readOnly(2),
        full(4)
    }

CucsLsApply ::= TEXTUAL-CONVENTION
    STATUS        current
    DESCRIPTION
        ""
    SYNTAX        INTEGER {
        onAssociation(1),
        runTime(2)
    }

CucsLsAssignment ::= TEXTUAL-CONVENTION
    STATUS        current
    DESCRIPTION
        ""
    SYNTAX        INTEGER {
        unassigned(0),
        assigned(1),
        failed(2)
    }

CucsLsAssocState ::= TEXTUAL-CONVENTION
    STATUS        current
    DESCRIPTION
        ""
    SYNTAX        INTEGER {
        unassociated(0),
        associating(1),
        associated(2),
        disassociating(3),
        failed(4)
    }

CucsLsComputeBindingOperState ::= TEXTUAL-CONVENTION
    STATUS        current
    DESCRIPTION
        ""
    SYNTAX        INTEGER {
        unused(0),
        used(1),
        failedToApply(2)
    }

CucsLsConfigIssues ::= TEXTUAL-CONVENTION
    STATUS        current
    DESCRIPTION
        ""
    SYNTAX        BITS {
        insufficientResources(0),
        vnicCapacity(1),
        vhbaCapacity(2),
        fcoeCapacity(3),
        switchVirtualIfCapacity(4),
        macAddressAssignment(5),
        wwpnAssignment(6),
        wwnnAssignment(7),
        systemUuidAssignment(8),
        bootOrderSanImagePath(9),
        bootOrderPxe(10),
        computeUndiscovered(11),
        adaptorProtectedEthCapability(12),
        adaptorFcoeCapability(13),
        incompatibleNumberOfLocalDisks(14),
        adaptorRequirement(15),
        memoryRequirement(16),
        processorRequirement(17),
        serverPositionRequirement(18),
        computeUnavailable(19),
        wwnnDerivationFromVhba(20),
        bootConfigurationInvalid(21),
        connectionPlacement(22),
        wwpnDerivationVirtualizedPort(23),
        macDerivationVirtualizedPort(24),
        qosPolicyInvalid(25),
        vlanPortCapacity(26),
        physicalRequirement(27),
        destructiveLocalDiskConfig(28),
        powerGroupRequirement(29),
        migration(30),
        incompatibleBiosImage(31),
        incompatibleRaidLevel(33),
        invalidWwn(34),
        insufficientPowerBudget(35),
        bootipPolicyInvalid(36),
        hostimgPolicyInvalid(37),
        imgsecPolicyInvalid(38),
        provsrvPolicyInvalid(39)
    }

CucsLsConfigState ::= TEXTUAL-CONVENTION
    STATUS        current
    DESCRIPTION
        ""
    SYNTAX        INTEGER {
        notApplied(0),
        applying(1),
        failedToApply(2),
        applied(3)
    }

CucsLsOperState ::= TEXTUAL-CONVENTION
    STATUS        current
    DESCRIPTION
        ""
    SYNTAX        INTEGER {
        indeterminate(0),
        unassociated(1),
        ok(10),
        discovery(11),
        config(12),
        unconfig(13),
        powerOff(14),
        restart(15),
        maintenance(20),
        test(21),
        computeMismatch(29),
        computeFailed(30),
        degraded(31),
        discoveryFailed(32),
        configFailure(33),
        unconfigFailed(34),
        testFailed(35),
        maintenanceFailed(36),
        removed(40),
        disabled(41),
        inaccessible(50),
        thermalProblem(60),
        powerProblem(61),
        voltageProblem(62),
        inoperable(63),
        decomissioning(101),
        biosRestore(201),
        cmosReset(202),
        diagnostics(203),
        diagnosticsFailed(204),
        pendingReboot(210),
        pendingReassociation(211)
    }

CucsLsOwner ::= TEXTUAL-CONVENTION
    STATUS        current
    DESCRIPTION
        ""
    SYNTAX        INTEGER {
        management(1),
        physicalInherit(2),
        physicalDefaultConfig(4),
        tier(8)
    }

CucsLsPowerState ::= TEXTUAL-CONVENTION
    STATUS        current
    DESCRIPTION
        ""
    SYNTAX        INTEGER {
        down(0),
        up(1),
        cycleImmediate(2),
        cycleWait(3),
        hardResetImmediate(4),
        hardResetWait(5),
        softShutDown(6),
        softShutDownOnly(7),
        cmosResetImmediate(12),
        bmcResetImmediate(13),
        bmcResetWait(14),
        diagnosticInterrupt(15),
        kvmReset(16)
    }

CucsLsServerFsmTaskFlags ::= TEXTUAL-CONVENTION
    STATUS        current
    DESCRIPTION
        ""
    SYNTAX        BITS {
        samDmeLsServerConfigureModification(49),
        samDmeLsServerConfigureFinalDisassoc(50)
    }

CucsLsServerFsmTaskItem ::= TEXTUAL-CONVENTION
    STATUS        current
    DESCRIPTION
        ""
    SYNTAX        INTEGER {
        nop(0),
        configure(965)
    }

CucsLsType ::= TEXTUAL-CONVENTION
    STATUS        current
    DESCRIPTION
        ""
    SYNTAX        INTEGER {
        instance(0),
        initialTemplate(1),
        updatingTemplate(2)
    }

CucsLsbootLanAccess ::= TEXTUAL-CONVENTION
    STATUS        current
    DESCRIPTION
        ""
    SYNTAX        INTEGER {
        readWrite(0),
        readOnly(1)
    }

CucsLsbootLanOrder ::= TEXTUAL-CONVENTION
    STATUS        current
    DESCRIPTION
        ""
    SYNTAX        INTEGER {
        n1(1),
        n2(2),
        n3(3),
        n4(4)
    }

CucsLsbootLanType ::= TEXTUAL-CONVENTION
    STATUS        current
    DESCRIPTION
        ""
    SYNTAX        INTEGER {
        virtualMedia(1),
        storage(2),
        lan(3)
    }

CucsLsbootLanBootProt ::= TEXTUAL-CONVENTION
    STATUS        current
    DESCRIPTION
        ""
    SYNTAX        INTEGER {
        pxe(0),
        gpxe(1),
        iSCSI(2)
    }

CucsLsbootLanImagePathType ::= TEXTUAL-CONVENTION
    STATUS        current
    DESCRIPTION
        ""
    SYNTAX        INTEGER {
        primary(0),
        secondary(1)
    }

CucsLsbootPurpose ::= TEXTUAL-CONVENTION
    STATUS        current
    DESCRIPTION
        ""
    SYNTAX        INTEGER {
        utility(1),
        operational(2)
    }

CucsLsbootSanImageType ::= TEXTUAL-CONVENTION
    STATUS        current
    DESCRIPTION
        ""
    SYNTAX        INTEGER {
        primary(0),
        secondary(1)
    }

CucsLsbootSanImagePathType ::= TEXTUAL-CONVENTION
    STATUS        current
    DESCRIPTION
        ""
    SYNTAX        INTEGER {
        primary(0),
        secondary(1)
    }

CucsLsbootStorageAccess ::= TEXTUAL-CONVENTION
    STATUS        current
    DESCRIPTION
        ""
    SYNTAX        INTEGER {
        readWrite(0),
        readOnly(1)
    }

CucsLsbootStorageOrder ::= TEXTUAL-CONVENTION
    STATUS        current
    DESCRIPTION
        ""
    SYNTAX        INTEGER {
        n1(1),
        n2(2),
        n3(3),
        n4(4)
    }

CucsLsbootStorageType ::= TEXTUAL-CONVENTION
    STATUS        current
    DESCRIPTION
        ""
    SYNTAX        INTEGER {
        virtualMedia(1),
        storage(2),
        lan(3)
    }

CucsLsbootVirtualMediaAccess ::= TEXTUAL-CONVENTION
    STATUS        current
    DESCRIPTION
        ""
    SYNTAX        INTEGER {
        readWrite(0),
        readOnly(1)
    }

CucsLsbootVirtualMediaOrder ::= TEXTUAL-CONVENTION
    STATUS        current
    DESCRIPTION
        ""
    SYNTAX        INTEGER {
        n1(1),
        n2(2),
        n3(3),
        n4(4)
    }

CucsLsbootVirtualMediaType ::= TEXTUAL-CONVENTION
    STATUS        current
    DESCRIPTION
        ""
    SYNTAX        INTEGER {
        virtualMedia(1),
        storage(2),
        lan(3)
    }

CucsLsmaintAckChangeDetails ::= TEXTUAL-CONVENTION
    STATUS        current
    DESCRIPTION
        ""
    SYNTAX        BITS {
        binding(0),
        hostVirtEthIf(1),
        hostNonvirtEthIf(2),
        hostEthIfQos(3),
        hostEthIfNwCtrl(4),
        hostVirtFcIf(6),
        hostNonvirtFcIf(7),
        hostVirtFcIfPersBind(8),
        hostNonvirtFcIfPersBind(9),
        vif(10),
        vlan(11),
        vsan(12),
        ip(13),
        bootOrder(14),
        bootLocalStorage(16),
        bootVirtVnic(18),
        bootNonvirtVnic(19),
        biosFw(20),
        storageControllerFw(21),
        bootNonvirtPxe(22),
        adaptorNwFw(23),
        mgmtControllerFw(24),
        localDiskPolicy(25),
        pin(26),
        sol(27),
        epAuth(28),
        biosProfile(29),
        checkpoint(30),
        implicitReboot(31),
        implicitHostFcIfProfileRedeploy(32),
        boardControllerFw(33),
        hostEthIfQosHostControl(40),
        localDiskFw(41),
        implicitHostEthIfProfileRedeploy(42)
    }

CucsLsmaintAckChanges ::= TEXTUAL-CONVENTION
    STATUS        current
    DESCRIPTION
        ""
    SYNTAX        BITS {
        serverIdentity(0),
        storage(1),
        networking(2),
        vnicVhbaPlacement(3),
        serverAssignment(4),
        operationalPolicies(5)
    }

CucsLsmaintAckDisr ::= TEXTUAL-CONVENTION
    STATUS        current
    DESCRIPTION
        ""
    SYNTAX        BITS {
        upTime(0)
    }

CucsLsmaintChangeMode ::= TEXTUAL-CONVENTION
    STATUS        current
    DESCRIPTION
        ""
    SYNTAX        INTEGER {
        noChange(0),
        unconfig(1),
        forceUnconfig(2),
        rediscover(4),
        config(8),
        diagConfig(16),
        diagUnconfig(32),
        removeConfig(64),
        diag(128),
        configEvaluation(256)
    }

CucsMemoryAdminState ::= TEXTUAL-CONVENTION
    STATUS        current
    DESCRIPTION
        ""
    SYNTAX        INTEGER {
        policy(1),
        resetErrors(2)
    }

CucsMemoryArrayId ::= TEXTUAL-CONVENTION
    STATUS        current
    DESCRIPTION
        ""
    SYNTAX        Gauge32 (1..8)

CucsMemoryArrayEnvStatsThresholded ::= TEXTUAL-CONVENTION
    STATUS        current
    DESCRIPTION
        ""
    SYNTAX        BITS {
        inputCurrent(0),
        inputCurrentAvg(1),
        inputCurrentMax(2),
        inputCurrentMin(3)
    }

CucsMemoryArrayEnvStatsHistThresholded ::= TEXTUAL-CONVENTION
    STATUS        current
    DESCRIPTION
        ""
    SYNTAX        BITS {
        inputCurrent(0),
        inputCurrentAvg(1),
        inputCurrentMax(2),
        inputCurrentMin(3)
    }

CucsMemoryBufferUnitId ::= TEXTUAL-CONVENTION
    STATUS        current
    DESCRIPTION
        ""
    SYNTAX        Gauge32 (1..16)

CucsMemoryBufferUnitEnvStatsThresholded ::= TEXTUAL-CONVENTION
    STATUS        current
    DESCRIPTION
        ""
    SYNTAX        BITS {
        temperature(0),
        temperatureAvg(1),
        temperatureMax(2),
        temperatureMin(3)
    }

CucsMemoryBufferUnitEnvStatsHistThresholded ::= TEXTUAL-CONVENTION
    STATUS        current
    DESCRIPTION
        ""
    SYNTAX        BITS {
        temperature(0),
        temperatureAvg(1),
        temperatureMax(2),
        temperatureMin(3)
    }

CucsMemoryErrorCorrection ::= TEXTUAL-CONVENTION
    STATUS        current
    DESCRIPTION
        ""
    SYNTAX        INTEGER {
        undiscovered(0),
        other(1),
        unknown(2),
        none(3),
        parity(4),
        singleBitECC(5),
        multiBitECC(6),
        crc(7)
    }

CucsMemoryErrorStatsThresholded ::= TEXTUAL-CONVENTION
    STATUS        current
    DESCRIPTION
        ""
    SYNTAX        BITS {
        addressParityErrors(0),
        eccMultibitErrors(1),
        eccSinglebitErrors(2),
        mismatchErrors(3)
    }

CucsMemoryFormFactor ::= TEXTUAL-CONVENTION
    STATUS        current
    DESCRIPTION
        ""
    SYNTAX        INTEGER {
        undiscovered(0),
        other(1),
        unknown(2),
        simm(3),
        dimm(9),
        tsop(10),
        rimm(12),
        sodimm(13),
        srimm(14),
        fbDimm(15)
    }

CucsMemoryIssues ::= TEXTUAL-CONVENTION
    STATUS        current
    DESCRIPTION
        ""
    SYNTAX        BITS {
        uncorrectableEccError(0),
        correctableEccError(1),
        addressParityError(2),
        memoryMismatchError(3)
    }

CucsMemoryRuntimeThresholded ::= TEXTUAL-CONVENTION
    STATUS        current
    DESCRIPTION
        ""
    SYNTAX        BITS {
        available(0),
        availableAvg(1),
        availableMax(2),
        availableMin(3),
        cached(4),
        cachedAvg(5),
        cachedMax(6),
        cachedMin(7),
        total(8),
        totalAvg(9),
        totalMax(10),
        totalMin(11)
    }

CucsMemoryRuntimeType ::= TEXTUAL-CONVENTION
    STATUS        current
    DESCRIPTION
        ""
    SYNTAX        INTEGER {
        swap(1),
        total(2)
    }

CucsMemoryRuntimeHistThresholded ::= TEXTUAL-CONVENTION
    STATUS        current
    DESCRIPTION
        ""
    SYNTAX        BITS {
        available(0),
        availableAvg(1),
        availableMax(2),
        availableMin(3),
        cached(4),
        cachedAvg(5),
        cachedMax(6),
        cachedMin(7),
        total(8),
        totalAvg(9),
        totalMax(10),
        totalMin(11)
    }

CucsMemoryType ::= TEXTUAL-CONVENTION
    STATUS        current
    DESCRIPTION
        ""
    SYNTAX        INTEGER {
        undiscovered(0),
        other(1),
        unknown(2),
        dram(3),
        edram(4),
        vram(5),
        sram(6),
        ram(7),
        rom(8),
        flash(9),
        eeprom(10),
        feprom(11),
        eprom(12),
        cdram(13),
        n3DRAM(14),
        sdram(15),
        sgram(16),
        rdram(17),
        ddr(18),
        ddr2(19),
        ddr2FbDimm(20),
        ddr3(24),
        fbd2(25)
    }

CucsMemoryUnitEnvStatsThresholded ::= TEXTUAL-CONVENTION
    STATUS        current
    DESCRIPTION
        ""
    SYNTAX        BITS {
        temperature(0),
        temperatureAvg(1),
        temperatureMax(2),
        temperatureMin(3)
    }

CucsMemoryUnitEnvStatsHistThresholded ::= TEXTUAL-CONVENTION
    STATUS        current
    DESCRIPTION
        ""
    SYNTAX        BITS {
        temperature(0),
        temperatureAvg(1),
        temperatureMax(2),
        temperatureMin(3)
    }

CucsMemoryVisibility ::= TEXTUAL-CONVENTION
    STATUS        current
    DESCRIPTION
        ""
    SYNTAX        INTEGER {
        unknown(0),
        yes(1),
        no(2)
    }

CucsMgmtAccess ::= TEXTUAL-CONVENTION
    STATUS        current
    DESCRIPTION
        ""
    SYNTAX        INTEGER {
        unspecified(0),
        inBand(1),
        outOfBand(2),
        internal(4),
        virtual(8)
    }

CucsMgmtAdminState ::= TEXTUAL-CONVENTION
    STATUS        current
    DESCRIPTION
        ""
    SYNTAX        INTEGER {
        disable(0),
        enable(1)
    }

CucsMgmtBackupPostAction ::= TEXTUAL-CONVENTION
    STATUS        current
    DESCRIPTION
        ""
    SYNTAX        INTEGER {
        none(0),
        remove(1)
    }

CucsMgmtBackupProto ::= TEXTUAL-CONVENTION
    STATUS        current
    DESCRIPTION
        ""
    SYNTAX        INTEGER {
        none(0),
        ftp(1),
        tftp(2),
        scp(3),
        http(4),
        sftp(5)
    }

CucsMgmtBackupFsmTaskItem ::= TEXTUAL-CONVENTION
    STATUS        current
    DESCRIPTION
        ""
    SYNTAX        INTEGER {
        nop(0),
        backup(290)
    }

CucsMgmtBackupJob ::= TEXTUAL-CONVENTION
    STATUS        current
    DESCRIPTION
        ""
    SYNTAX        INTEGER {
        immediate(2)
    }

CucsMgmtBackupType ::= TEXTUAL-CONVENTION
    STATUS        current
    DESCRIPTION
        ""
    SYNTAX        INTEGER {
        fullState(1),
        configAll(2),
        configSystem(3),
        configLogical(4)
    }

CucsMgmtControllerFsmTaskFlags ::= TEXTUAL-CONVENTION
    STATUS        current
    DESCRIPTION
        ""
    SYNTAX        BITS {
        samDmeMgmtControllerUpdateSwitchActivate(14),
        samDmeMgmtControllerUpdateSwitchReset(15)
    }

CucsMgmtControllerFsmTaskItem ::= TEXTUAL-CONVENTION
    STATUS        current
    DESCRIPTION
        ""
    SYNTAX        INTEGER {
        nop(0),
        extMgmtIfConfig(17),
        updateSwitch(248),
        updateIOM(253),
        activateIOM(256),
        updateBMC(259),
        activateBMC(262),
        updateUCSManager(467),
        sysConfig(474),
        online(1059)
    }

CucsMgmtEntityChassisDeviceIoState1 ::= TEXTUAL-CONVENTION
    STATUS        current
    DESCRIPTION
        ""
    SYNTAX        INTEGER {
        unknown(0),
        ok(1),
        openError(2),
        readError(3),
        writeError(4)
    }

CucsMgmtEntityChassisDeviceIoState2 ::= TEXTUAL-CONVENTION
    STATUS        current
    DESCRIPTION
        ""
    SYNTAX        INTEGER {
        unknown(0),
        ok(1),
        openError(2),
        readError(3),
        writeError(4)
    }

CucsMgmtEntityChassisDeviceIoState3 ::= TEXTUAL-CONVENTION
    STATUS        current
    DESCRIPTION
        ""
    SYNTAX        INTEGER {
        unknown(0),
        ok(1),
        openError(2),
        readError(3),
        writeError(4)
    }

CucsMgmtEntityHaFailureReason ::= TEXTUAL-CONVENTION
    STATUS        current
    DESCRIPTION
        ""
    SYNTAX        INTEGER {
        none(0),
        nodeDown(1),
        peerNodeDown(2),
        mgmtServicesUnresponsive(3),
        peerMgmtServicesUnresponsive(4),
        chassisConfigIncomplete(5),
        peerChassisConfigIncomplete(6),
        networkInterfaceDown(7)
    }

CucsMgmtEntityHaReadiness ::= TEXTUAL-CONVENTION
    STATUS        current
    DESCRIPTION
        ""
    SYNTAX        INTEGER {
        unknown(0),
        ready(1),
        downgraded(2),
        notReady(3)
    }

CucsMgmtEntityLeadership ::= TEXTUAL-CONVENTION
    STATUS        current
    DESCRIPTION
        ""
    SYNTAX        INTEGER {
        unknown(0),
        primary(1),
        subordinate(2),
        inapplicable(3),
        electionInProgress(4),
        electionFailed(5)
    }

CucsMgmtEntityMgmtServicesState ::= TEXTUAL-CONVENTION
    STATUS        current
    DESCRIPTION
        ""
    SYNTAX        INTEGER {
        unknown(0),
        up(1),
        unresponsive(2),
        down(3),
        switchoverInProgress(4)
    }

CucsMgmtEntityProblems ::= TEXTUAL-CONVENTION
    STATUS        current
    DESCRIPTION
        ""
    SYNTAX        BITS {
        leadership(0),
        membership(1),
        umbilical(2),
        haReady(3),
        versionMismatch(4)
    }

CucsMgmtEntityState ::= TEXTUAL-CONVENTION
    STATUS        current
    DESCRIPTION
        ""
    SYNTAX        INTEGER {
        unknown(0),
        up(1),
        down(2)
    }

CucsMgmtEntityUmbilicalState ::= TEXTUAL-CONVENTION
    STATUS        current
    DESCRIPTION
        ""
    SYNTAX        INTEGER {
        unknown(0),
        degraded(1),
        full(2),
        failed(3)
    }

CucsMgmtIfFsmTaskItem ::= TEXTUAL-CONVENTION
    STATUS        current
    DESCRIPTION
        ""
    SYNTAX        INTEGER {
        nop(0),
        swMgmtOobIfConfig(277),
        swMgmtInbandIfConfig(279),
        virtualIfConfig(281),
        enableVip(284),
        disableVip(286),
        enableHA(288)
    }

CucsMgmtImportAction ::= TEXTUAL-CONVENTION
    STATUS        current
    DESCRIPTION
        ""
    SYNTAX        INTEGER {
        merge(0),
        replace(1)
    }

CucsMgmtImporterPostAction ::= TEXTUAL-CONVENTION
    STATUS        current
    DESCRIPTION
        ""
    SYNTAX        INTEGER {
        none(0),
        remove(1)
    }

CucsMgmtImporterProto ::= TEXTUAL-CONVENTION
    STATUS        current
    DESCRIPTION
        ""
    SYNTAX        INTEGER {
        none(0),
        ftp(1),
        tftp(2),
        scp(3),
        http(4),
        sftp(5)
    }

CucsMgmtImporterFsmTaskItem ::= TEXTUAL-CONVENTION
    STATUS        current
    DESCRIPTION
        ""
    SYNTAX        INTEGER {
        nop(0),
        import(293)
    }

CucsMgmtIntAuthPolicyMethod ::= TEXTUAL-CONVENTION
    STATUS        current
    DESCRIPTION
        ""
    SYNTAX        INTEGER {
        none(0),
        password(1)
    }

CucsMgmtStateQual ::= TEXTUAL-CONVENTION
    STATUS        current
    DESCRIPTION
        ""
    SYNTAX        INTEGER {
        unspecified(0),
        valid(1),
        misconnected(2)
    }

CucsMgmtSubject ::= TEXTUAL-CONVENTION
    STATUS        current
    DESCRIPTION
        ""
    SYNTAX        INTEGER {
        unknown(0),
        blade(1),
        chassis(2),
        system(4),
        switch(8),
        adaptor(16),
        iocard(32),
        boardController(64)
    }

CucsMgmtUpgradeStatus ::= TEXTUAL-CONVENTION
    STATUS        current
    DESCRIPTION
        ""
    SYNTAX        BITS {
        hwChangeDetected(0),
        fwChangeDetected(1),
        hwIncompatible(2),
        fwIncompatible(3),
        unsupportedHwVersion(4),
        unsupportedFwVersion(5),
        hwChangeSuccess(6),
        fwChangeSuccess(7)
    }

CucsNetworkConnectionType ::= TEXTUAL-CONVENTION
    STATUS        current
    DESCRIPTION
        ""
    SYNTAX        BITS {
        lan(0),
        san(1),
        ipc(2)
    }

CucsNetworkElementOperability ::= TEXTUAL-CONVENTION
    STATUS        current
    DESCRIPTION
        ""
    SYNTAX        INTEGER {
        unknown(0),
        operable(1),
        inoperable(2)
    }

CucsNetworkIfStatsType ::= TEXTUAL-CONVENTION
    STATUS        current
    DESCRIPTION
        ""
    SYNTAX        INTEGER {
        generic(0),
        broadcast(1),
        multicast(2),
        unicast(3),
        total(4)
    }

CucsNetworkIfStatsUnits ::= TEXTUAL-CONVENTION
    STATUS        current
    DESCRIPTION
        ""
    SYNTAX        INTEGER {
        raw(0),
        packets(1),
        octets(2)
    }

CucsNetworkIfStatus ::= TEXTUAL-CONVENTION
    STATUS        current
    DESCRIPTION
        ""
    SYNTAX        INTEGER {
        unknown(0),
        down(1),
        up(2)
    }

CucsNetworkLocale ::= TEXTUAL-CONVENTION
    STATUS        current
    DESCRIPTION
        ""
    SYNTAX        BITS {
        server(0),
        chassis(1),
        internal(2),
        external(3)
    }

CucsNetworkPhysEpIfType ::= TEXTUAL-CONVENTION
    STATUS        current
    DESCRIPTION
        ""
    SYNTAX        INTEGER {
        unknown(0),
        physical(1),
        aggregation(2),
        virtual(3)
    }

CucsNetworkPortOperState ::= TEXTUAL-CONVENTION
    STATUS        current
    DESCRIPTION
        ""
    SYNTAX        INTEGER {
        indeterminate(0),
        up(1),
        adminDown(2),
        linkDown(3),
        failed(4),
        noLicense(5),
        linkUp(6),
        hardwareFailure(7),
        softwareFailure(8),
        errorDisabled(9),
        sfpNotPresent(10)
    }

CucsNetworkPortRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsNetworkPortType ::= TEXTUAL-CONVENTION
    STATUS        current
    DESCRIPTION
        ""
    SYNTAX        INTEGER {
        unknown(0),
        physical(1),
        aggregation(2),
        virtual(3)
    }

CucsNetworkSide ::= TEXTUAL-CONVENTION
    STATUS        current
    DESCRIPTION
        ""
    SYNTAX        INTEGER {
        left(0),
        right(1)
    }

CucsNetworkSwitchId ::= TEXTUAL-CONVENTION
    STATUS        current
    DESCRIPTION
        ""
    SYNTAX        INTEGER {
        none(0),
        a(1),
        b(2)
    }

CucsNetworkTransport ::= TEXTUAL-CONVENTION
    STATUS        current
    DESCRIPTION
        ""
    SYNTAX        BITS {
        ether(0),
        dce(1),
        fc(2)
    }

CucsNetworkVnetEpIfType ::= TEXTUAL-CONVENTION
    STATUS        current
    DESCRIPTION
        ""
    SYNTAX        INTEGER {
        unknown(0),
        physical(1),
        aggregation(2),
        virtual(3)
    }

CucsNwctrlAdminState ::= TEXTUAL-CONVENTION
    STATUS        current
    DESCRIPTION
        ""
    SYNTAX        INTEGER {
        disabled(0),
        enabled(1)
    }

CucsNwctrlLinkFailAction ::= TEXTUAL-CONVENTION
    STATUS        current
    DESCRIPTION
        ""
    SYNTAX        INTEGER {
        linkDown(0),
        warning(1)
    }

CucsOrgLevel ::= TEXTUAL-CONVENTION
    STATUS        current
    DESCRIPTION
        ""
    SYNTAX        INTEGER {
        root(0),
        n1(1),
        n2(2),
        n3(3),
        n4(4),
        n5(5)
    }

CucsOsOsType ::= TEXTUAL-CONVENTION
    STATUS        current
    DESCRIPTION
        ""
    SYNTAX        INTEGER {
        unspecified(0),
        pnuOS(1),
        linux(2),
        windows(3),
        solaris(4),
        vmwareESX(5)
    }

CucsPciEquipSlotId ::= TEXTUAL-CONVENTION
    STATUS        current
    DESCRIPTION
        ""
    SYNTAX        Gauge32 (1..5000)

CucsPkiEpFsmTaskItem ::= TEXTUAL-CONVENTION
    STATUS        current
    DESCRIPTION
        ""
    SYNTAX        INTEGER {
        nop(0),
        updateEp(206)
    }

CucsPkiKeyringState ::= TEXTUAL-CONVENTION
    STATUS        current
    DESCRIPTION
        ""
    SYNTAX        INTEGER {
        started(1),
        created(2),
        reqCreated(3),
        tpSet(4),
        completed(5)
    }

CucsPkiModulus ::= TEXTUAL-CONVENTION
    STATUS        current
    DESCRIPTION
        ""
    SYNTAX        INTEGER {
        modinvalid(0),
        mod512(512),
        mod1024(1024),
        mod1536(1536),
        mod2048(2048)
    }

CucsPoolElementOwner ::= TEXTUAL-CONVENTION
    STATUS        current
    DESCRIPTION
        ""
    SYNTAX        INTEGER {
        endPoint(0),
        pool(1)
    }

CucsPortEncap ::= TEXTUAL-CONVENTION
    STATUS        current
    DESCRIPTION
        ""
    SYNTAX        INTEGER {
        unknown(0),
        dot1q(1),
        isl(2),
        negotiate(3),
        proprietary(4)
    }

CucsPortEthSpeed ::= TEXTUAL-CONVENTION
    STATUS        current
    DESCRIPTION
        ""
    SYNTAX        INTEGER {
        indeterminate(0),
        n1gbps(1),
        n10gbps(2)
    }

CucsPortGroupType ::= TEXTUAL-CONVENTION
    STATUS        current
    DESCRIPTION
        ""
    SYNTAX        INTEGER {
        switchEther(1),
        switchFc(4),
        host(8),
        fabric(16)
    }

CucsPortMode ::= TEXTUAL-CONVENTION
    STATUS        current
    DESCRIPTION
        ""
    SYNTAX        INTEGER {
        unknown(0),
        access(1),
        trunk(2),
        fabric(3),
        nProxy(4),
        f(5),
        e(6),
        sd(7)
    }

CucsPortPIoFsmTaskItem ::= TEXTUAL-CONVENTION
    STATUS        current
    DESCRIPTION
        ""
    SYNTAX        INTEGER {
        nop(0),
        inCompatSfpPresence(1014)
    }

CucsPortSpeed ::= TEXTUAL-CONVENTION
    STATUS        current
    DESCRIPTION
        ""
    SYNTAX        INTEGER {
        indeterminate(0),
        n1gbps(1),
        n2gbps(2),
        n4gbps(3),
        n8gbps(4),
        auto(5)
    }

CucsPortTrust ::= TEXTUAL-CONVENTION
    STATUS        current
    DESCRIPTION
        ""
    SYNTAX        INTEGER {
        trusted(0),
        untrusted(1)
    }

CucsPowerCapAction ::= TEXTUAL-CONVENTION
    STATUS        current
    DESCRIPTION
        ""
    SYNTAX        INTEGER {
        nothing(0),
        clockDown(1),
        throttled(2)
    }

CucsPowerChThrAction ::= TEXTUAL-CONVENTION
    STATUS        current
    DESCRIPTION
        ""
    SYNTAX        INTEGER {
        nothing(0),
        throttleBladeDisc(1),
        stopBladeDisc(2)
    }

CucsPowerGroupState ::= TEXTUAL-CONVENTION
    STATUS        current
    DESCRIPTION
        ""
    SYNTAX        BITS {
        capOk(0),
        capMismatch(1)
    }

CucsPowerGroupStatsThresholded ::= TEXTUAL-CONVENTION
    STATUS        current
    DESCRIPTION
        ""
    SYNTAX        BITS {
        power(0),
        powerAvg(1),
        powerMax(2),
        powerMin(3)
    }

CucsPowerGroupStatsHistThresholded ::= TEXTUAL-CONVENTION
    STATUS        current
    DESCRIPTION
        ""
    SYNTAX        BITS {
        power(0),
        powerAvg(1),
        powerMax(2),
        powerMin(3)
    }

CucsPowerMemberState ::= TEXTUAL-CONVENTION
    STATUS        current
    DESCRIPTION
        ""
    SYNTAX        INTEGER {
        uninitialized(0),
        capOk(1),
        fwMismatch(2),
        psuInsufficient(3),
        psuRedundancyFailed(4),
        capInsufficient(5)
    }

CucsPowerMgmtStyle ::= TEXTUAL-CONVENTION
    STATUS        current
    DESCRIPTION
        ""
    SYNTAX        INTEGER {
        manualPerBlade(0),
        intelligentPolicyDriven(1)
    }

CucsPowerOperState ::= TEXTUAL-CONVENTION
    STATUS        current
    DESCRIPTION
        ""
    SYNTAX        INTEGER {
        notCapped(0),
        discoveryRetry(3),
        nonCompliant(6),
        firmwareMismatch(7),
        budgeting(10),
        budgeted(11),
        deploying(12),
        deployed(13)
    }

CucsPowerPrioritySharing ::= TEXTUAL-CONVENTION
    STATUS        current
    DESCRIPTION
        ""
    SYNTAX        INTEGER {
        noPreference(0),
        highestPrioInChassis(1),
        highestPrioInPowerGroup(2)
    }

CucsPowerPsuState ::= TEXTUAL-CONVENTION
    STATUS        current
    DESCRIPTION
        ""
    SYNTAX        INTEGER {
        ok(0),
        insufficient(1)
    }

CucsPowerReallocation ::= TEXTUAL-CONVENTION
    STATUS        current
    DESCRIPTION
        ""
    SYNTAX        BITS {
        chassis(0)
    }

CucsPowerReqConflict ::= TEXTUAL-CONVENTION
    STATUS        current
    DESCRIPTION
        ""
    SYNTAX        INTEGER {
        ignore(0),
        failPlacement(1)
    }

CucsProcessorEnvStatsThresholded ::= TEXTUAL-CONVENTION
    STATUS        current
    DESCRIPTION
        ""
    SYNTAX        BITS {
        inputCurrent(0),
        inputCurrentAvg(1),
        inputCurrentMax(2),
        inputCurrentMin(3),
        temperature(4),
        temperatureAvg(5),
        temperatureMax(6),
        temperatureMin(7)
    }

CucsProcessorEnvStatsHistThresholded ::= TEXTUAL-CONVENTION
    STATUS        current
    DESCRIPTION
        ""
    SYNTAX        BITS {
        inputCurrent(0),
        inputCurrentAvg(1),
        inputCurrentMax(2),
        inputCurrentMin(3),
        temperature(4),
        temperatureAvg(5),
        temperatureMax(6),
        temperatureMin(7)
    }

CucsProcessorErrorStatsThresholded ::= TEXTUAL-CONVENTION
    STATUS        current
    DESCRIPTION
        ""
    SYNTAX        BITS {
        mirroringInterSockErrors(0),
        mirroringIntraSockErrors(1),
        smiLinkCorrErrors(2),
        smiLinkUncorrErrors(3),
        sparingErrors(4)
    }

CucsProcessorQualArch ::= TEXTUAL-CONVENTION
    STATUS        current
    DESCRIPTION
        ""
    SYNTAX        INTEGER {
        any(0),
        intelP4C(1),
        opteron(132),
        turion64(134),
        dualCoreOpteron(135),
        pentium4(178),
        xeon(179),
        xeonMP(181)
    }

CucsProcessorRuntimeThresholded ::= TEXTUAL-CONVENTION
    STATUS        current
    DESCRIPTION
        ""
    SYNTAX        BITS {
        load(0),
        loadAvg(1),
        loadMax(2),
        loadMin(3)
    }

CucsProcessorRuntimeHistThresholded ::= TEXTUAL-CONVENTION
    STATUS        current
    DESCRIPTION
        ""
    SYNTAX        BITS {
        load(0),
        loadAvg(1),
        loadMax(2),
        loadMin(3)
    }

CucsProcessorUnitArch ::= TEXTUAL-CONVENTION
    STATUS        current
    DESCRIPTION
        ""
    SYNTAX        INTEGER {
        any(0),
        intelP4C(1),
        opteron(132),
        turion64(134),
        dualCoreOpteron(135),
        pentium4(178),
        xeon(179),
        xeonMP(181)
    }

CucsQosHostControl ::= TEXTUAL-CONVENTION
    STATUS        current
    DESCRIPTION
        ""
    SYNTAX        INTEGER {
        none(0),
        full(1),
        fullWithException(2)
    }

CucsQosPriority ::= TEXTUAL-CONVENTION
    STATUS        current
    DESCRIPTION
        ""
    SYNTAX        INTEGER {
        fc(1),
        platinum(2),
        gold(3),
        silver(4),
        bronze(5),
        bestEffort(6)
    }

CucsQosclassDefinitionFsmTaskItem ::= TEXTUAL-CONVENTION
    STATUS        current
    DESCRIPTION
        ""
    SYNTAX        INTEGER {
        nop(0),
        configGlobalQoS(313)
    }

CucsQosclassEthBEAdminState ::= TEXTUAL-CONVENTION
    STATUS        current
    DESCRIPTION
        ""
    SYNTAX        INTEGER {
        disabled(0),
        enabled(1)
    }

CucsQosclassEthBEDrop ::= TEXTUAL-CONVENTION
    STATUS        current
    DESCRIPTION
        ""
    SYNTAX        INTEGER {
        drop(0),
        noDrop(1)
    }

CucsQosclassEthBEPriority ::= TEXTUAL-CONVENTION
    STATUS        current
    DESCRIPTION
        ""
    SYNTAX        INTEGER {
        fc(1),
        platinum(2),
        gold(3),
        silver(4),
        bronze(5),
        bestEffort(6)
    }

CucsQosclassEthClassifiedAdminState ::= TEXTUAL-CONVENTION
    STATUS        current
    DESCRIPTION
        ""
    SYNTAX        INTEGER {
        disabled(0),
        enabled(1)
    }

CucsQosclassEthClassifiedDrop ::= TEXTUAL-CONVENTION
    STATUS        current
    DESCRIPTION
        ""
    SYNTAX        INTEGER {
        drop(0),
        noDrop(1)
    }

CucsQosclassEthClassifiedPriority ::= TEXTUAL-CONVENTION
    STATUS        current
    DESCRIPTION
        ""
    SYNTAX        INTEGER {
        fc(1),
        platinum(2),
        gold(3),
        silver(4),
        bronze(5),
        bestEffort(6)
    }

CucsQosclassFcAdminState ::= TEXTUAL-CONVENTION
    STATUS        current
    DESCRIPTION
        ""
    SYNTAX        INTEGER {
        disabled(0),
        enabled(1)
    }

CucsQosclassFcDrop ::= TEXTUAL-CONVENTION
    STATUS        current
    DESCRIPTION
        ""
    SYNTAX        INTEGER {
        drop(0),
        noDrop(1)
    }

CucsQosclassFcPriority ::= TEXTUAL-CONVENTION
    STATUS        current
    DESCRIPTION
        ""
    SYNTAX        INTEGER {
        fc(1),
        platinum(2),
        gold(3),
        silver(4),
        bronze(5),
        bestEffort(6)
    }

CucsSolAdminState ::= TEXTUAL-CONVENTION
    STATUS        current
    DESCRIPTION
        ""
    SYNTAX        INTEGER {
        disable(0),
        enable(1)
    }

CucsSolSpeed ::= TEXTUAL-CONVENTION
    STATUS        current
    DESCRIPTION
        ""
    SYNTAX        INTEGER {
        n9600(6),
        n19200(7),
        n38400(8),
        n57600(9),
        n115200(10),
        defaultValue(9600)
    }

CucsStatsCollectionDomain ::= TEXTUAL-CONVENTION
    STATUS        current
    DESCRIPTION
        ""
    SYNTAX        INTEGER {
        unknown(0),
        chassis(2),
        port(4),
        host(5),
        adapter(6),
        server(7),
        fex(8)
    }

CucsStatsCollectionInterval ::= TEXTUAL-CONVENTION
    STATUS        current
    DESCRIPTION
        ""
    SYNTAX        INTEGER {
        n30seconds(30),
        n1minute(60),
        n2minutes(120),
        n5minutes(300)
    }

CucsStatsCollectionPolicyFsmTaskItem ::= TEXTUAL-CONVENTION
    STATUS        current
    DESCRIPTION
        ""
    SYNTAX        INTEGER {
        nop(0),
        updateEp(310)
    }

CucsStatsReportingInterval ::= TEXTUAL-CONVENTION
    STATUS        current
    DESCRIPTION
        ""
    SYNTAX        INTEGER {
        n2minutes(120),
        n15minutes(900),
        n30minutes(1800),
        n60minutes(3600),
        n2hours(7200),
        n4hours(14400),
        n8hours(28800)
    }

CucsStatsThr32DefinitionPropType ::= TEXTUAL-CONVENTION
    STATUS        current
    DESCRIPTION
        ""
    SYNTAX        INTEGER {
        uint32(1),
        uint64(2),
        float(3)
    }

CucsStatsThr32ValuePropType ::= TEXTUAL-CONVENTION
    STATUS        current
    DESCRIPTION
        ""
    SYNTAX        INTEGER {
        uint32(1),
        uint64(2),
        float(3)
    }

CucsStatsThr64DefinitionPropType ::= TEXTUAL-CONVENTION
    STATUS        current
    DESCRIPTION
        ""
    SYNTAX        INTEGER {
        uint32(1),
        uint64(2),
        float(3)
    }

CucsStatsThr64ValuePropType ::= TEXTUAL-CONVENTION
    STATUS        current
    DESCRIPTION
        ""
    SYNTAX        INTEGER {
        uint32(1),
        uint64(2),
        float(3)
    }

CucsStatsThrFloatDefinitionPropType ::= TEXTUAL-CONVENTION
    STATUS        current
    DESCRIPTION
        ""
    SYNTAX        INTEGER {
        uint32(1),
        uint64(2),
        float(3)
    }

CucsStatsThrFloatValuePropType ::= TEXTUAL-CONVENTION
    STATUS        current
    DESCRIPTION
        ""
    SYNTAX        INTEGER {
        uint32(1),
        uint64(2),
        float(3)
    }

CucsStatsThresholdDirection ::= TEXTUAL-CONVENTION
    STATUS        current
    DESCRIPTION
        ""
    SYNTAX        INTEGER {
        aboveNormal(1),
        belowNormal(2)
    }

CucsStorageConfiguration ::= TEXTUAL-CONVENTION
    STATUS        current
    DESCRIPTION
        ""
    SYNTAX        INTEGER {
        unknown(0),
        supported(1),
        notSupported(2)
    }

CucsStorageConnectionProtocol ::= TEXTUAL-CONVENTION
    STATUS        current
    DESCRIPTION
        ""
    SYNTAX        INTEGER {
        unspecified(0),
        sas(1),
        sata(2)
    }

CucsStorageControllerType ::= TEXTUAL-CONVENTION
    STATUS        current
    DESCRIPTION
        ""
    SYNTAX        INTEGER {
        sas(1),
        sata(2)
    }

CucsStorageControllerForm ::= TEXTUAL-CONVENTION
    STATUS        current
    DESCRIPTION
        ""
    SYNTAX        INTEGER {
        none(0),
        onBoard(1),
        mezzanine(2),
        pci(3),
        embedded(4)
    }

CucsStorageDisklessAction ::= TEXTUAL-CONVENTION
    STATUS        current
    DESCRIPTION
        ""
    SYNTAX        INTEGER {
        unspecified(0),
        yes(1),
        no(2)
    }

CucsStorageLocalDiskMode ::= TEXTUAL-CONVENTION
    STATUS        current
    DESCRIPTION
        ""
    SYNTAX        INTEGER {
        noLocalStorage(1),
        singleDisk(2),
        dualDisk(3),
        raidStriped(4),
        raidMirrored(5),
        bestEffortMirrored(6),
        bestEffortStriped(7),
        anyConfiguration(8),
        noRaid(9),
        raidStripedParity(10),
        raidStripedDualParity(11),
        raidMirroredStriped(12),
        bestEffortStripedParity(13),
        bestEffortStripedDualParity(14),
        bestEffortMirroredStriped(15)
    }

CucsStorageLocalDiskPartitionType ::= TEXTUAL-CONVENTION
    STATUS        current
    DESCRIPTION
        ""
    SYNTAX        INTEGER {
        none(1),
        swap(2),
        ext2(3),
        ext3(4),
        ntfs(5),
        fat32(6)
    }

CucsStorageLunType ::= TEXTUAL-CONVENTION
    STATUS        current
    DESCRIPTION
        ""
    SYNTAX        INTEGER {
        unspecified(0),
        simple(1),
        mirror(2),
        stripe(3),
        raid(4),
        stripeParity(5),
        stripeDualParity(6),
        mirrorStripe(7)
    }

CucsStorageTechnology ::= TEXTUAL-CONVENTION
    STATUS        current
    DESCRIPTION
        ""
    SYNTAX        INTEGER {
        unspecified(0),
        hdd(1),
        ssd(2)
    }

CucsSwAccessDomainLocale ::= TEXTUAL-CONVENTION
    STATUS        current
    DESCRIPTION
        ""
    SYNTAX        BITS {
        server(0),
        chassis(1),
        internal(2),
        external(3)
    }

CucsSwAccessDomainType ::= TEXTUAL-CONVENTION
    STATUS        current
    DESCRIPTION
        ""
    SYNTAX        BITS {
        lan(0),
        san(1),
        ipc(2)
    }

CucsSwAccessDomainFsmTaskItem ::= TEXTUAL-CONVENTION
    STATUS        current
    DESCRIPTION
        ""
    SYNTAX        INTEGER {
        nop(0),
        deploy(222)
    }

CucsSwAccessEpLocale ::= TEXTUAL-CONVENTION
    STATUS        current
    DESCRIPTION
        ""
    SYNTAX        BITS {
        server(0),
        chassis(1),
        internal(2),
        external(3)
    }

CucsSwAccessEpTransport ::= TEXTUAL-CONVENTION
    STATUS        current
    DESCRIPTION
        ""
    SYNTAX        BITS {
        ether(0),
        dce(1),
        fc(2)
    }

CucsSwBorderDomainLocale ::= TEXTUAL-CONVENTION
    STATUS        current
    DESCRIPTION
        ""
    SYNTAX        BITS {
        server(0),
        chassis(1),
        internal(2),
        external(3)
    }

CucsSwBorderEpLocale ::= TEXTUAL-CONVENTION
    STATUS        current
    DESCRIPTION
        ""
    SYNTAX        BITS {
        server(0),
        chassis(1),
        internal(2),
        external(3)
    }

CucsSwBorderPcLocale ::= TEXTUAL-CONVENTION
    STATUS        current
    DESCRIPTION
        ""
    SYNTAX        BITS {
        server(0),
        chassis(1),
        internal(2),
        external(3)
    }

CucsSwCIoEpIfType ::= TEXTUAL-CONVENTION
    STATUS        current
    DESCRIPTION
        ""
    SYNTAX        INTEGER {
        unknown(0),
        physical(1),
        aggregation(2),
        virtual(3)
    }

CucsSwEnvStatsThresholded ::= TEXTUAL-CONVENTION
    STATUS        current
    DESCRIPTION
        ""
    SYNTAX        BITS {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31)
    }

CucsSwEnvStatsHistThresholded ::= TEXTUAL-CONVENTION
    STATUS        current
    DESCRIPTION
        ""
    SYNTAX        BITS {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31)
    }

CucsSwEstcEpLocale ::= TEXTUAL-CONVENTION
    STATUS        current
    DESCRIPTION
        ""
    SYNTAX        BITS {
        server(0),
        chassis(1),
        internal(2),
        external(3)
    }

CucsSwEthEstcEpTransport ::= TEXTUAL-CONVENTION
    STATUS        current
    DESCRIPTION
        ""
    SYNTAX        BITS {
        ether(0),
        dce(1),
        fc(2)
    }

CucsSwEthEstcPcTransport ::= TEXTUAL-CONVENTION
    STATUS        current
    DESCRIPTION
        ""
    SYNTAX        BITS {
        ether(0),
        dce(1),
        fc(2)
    }

CucsSwEthLanBorderTransport ::= TEXTUAL-CONVENTION
    STATUS        current
    DESCRIPTION
        ""
    SYNTAX        BITS {
        ether(0),
        dce(1),
        fc(2)
    }

CucsSwEthLanBorderFsmTaskItem ::= TEXTUAL-CONVENTION
    STATUS        current
    DESCRIPTION
        ""
    SYNTAX        INTEGER {
        nop(0),
        deploy(224)
    }

CucsSwEthLanEpTransport ::= TEXTUAL-CONVENTION
    STATUS        current
    DESCRIPTION
        ""
    SYNTAX        BITS {
        ether(0),
        dce(1),
        fc(2)
    }

CucsSwEthLanMonTransport ::= TEXTUAL-CONVENTION
    STATUS        current
    DESCRIPTION
        ""
    SYNTAX        BITS {
        ether(0),
        dce(1),
        fc(2)
    }

CucsSwEthLanPcTransport ::= TEXTUAL-CONVENTION
    STATUS        current
    DESCRIPTION
        ""
    SYNTAX        BITS {
        ether(0),
        dce(1),
        fc(2)
    }

CucsSwEthMonTransport ::= TEXTUAL-CONVENTION
    STATUS        current
    DESCRIPTION
        ""
    SYNTAX        BITS {
        ether(0),
        dce(1),
        fc(2)
    }

CucsSwEthMonType ::= TEXTUAL-CONVENTION
    STATUS        current
    DESCRIPTION
        ""
    SYNTAX        BITS {
        lan(0),
        san(1),
        ipc(2)
    }

CucsSwEthMonDestEpTransport ::= TEXTUAL-CONVENTION
    STATUS        current
    DESCRIPTION
        ""
    SYNTAX        BITS {
        ether(0),
        dce(1),
        fc(2)
    }

CucsSwEthMonFsmTaskItem ::= TEXTUAL-CONVENTION
    STATUS        current
    DESCRIPTION
        ""
    SYNTAX        INTEGER {
        nop(0),
        deploy(953)
    }

CucsSwEthMonSrcEpTransport ::= TEXTUAL-CONVENTION
    STATUS        current
    DESCRIPTION
        ""
    SYNTAX        BITS {
        ether(0),
        dce(1),
        fc(2)
    }

CucsSwEthTargetEpTransport ::= TEXTUAL-CONVENTION
    STATUS        current
    DESCRIPTION
        ""
    SYNTAX        BITS {
        ether(0),
        dce(1),
        fc(2)
    }

CucsSwFcEstcEpTransport ::= TEXTUAL-CONVENTION
    STATUS        current
    DESCRIPTION
        ""
    SYNTAX        BITS {
        ether(0),
        dce(1),
        fc(2)
    }

CucsSwFcMonTransport ::= TEXTUAL-CONVENTION
    STATUS        current
    DESCRIPTION
        ""
    SYNTAX        BITS {
        ether(0),
        dce(1),
        fc(2)
    }

CucsSwFcMonType ::= TEXTUAL-CONVENTION
    STATUS        current
    DESCRIPTION
        ""
    SYNTAX        BITS {
        lan(0),
        san(1),
        ipc(2)
    }

CucsSwFcMonDestEpTransport ::= TEXTUAL-CONVENTION
    STATUS        current
    DESCRIPTION
        ""
    SYNTAX        BITS {
        ether(0),
        dce(1),
        fc(2)
    }

CucsSwFcMonFsmTaskItem ::= TEXTUAL-CONVENTION
    STATUS        current
    DESCRIPTION
        ""
    SYNTAX        INTEGER {
        nop(0),
        deploy(955)
    }

CucsSwFcMonSrcEpTransport ::= TEXTUAL-CONVENTION
    STATUS        current
    DESCRIPTION
        ""
    SYNTAX        BITS {
        ether(0),
        dce(1),
        fc(2)
    }

CucsSwFcSanBorderTransport ::= TEXTUAL-CONVENTION
    STATUS        current
    DESCRIPTION
        ""
    SYNTAX        BITS {
        ether(0),
        dce(1),
        fc(2)
    }

CucsSwFcSanBorderFsmTaskItem ::= TEXTUAL-CONVENTION
    STATUS        current
    DESCRIPTION
        ""
    SYNTAX        INTEGER {
        nop(0),
        deploy(226)
    }

CucsSwFcSanEpTransport ::= TEXTUAL-CONVENTION
    STATUS        current
    DESCRIPTION
        ""
    SYNTAX        BITS {
        ether(0),
        dce(1),
        fc(2)
    }

CucsSwFcSanMonTransport ::= TEXTUAL-CONVENTION
    STATUS        current
    DESCRIPTION
        ""
    SYNTAX        BITS {
        ether(0),
        dce(1),
        fc(2)
    }

CucsSwFcSanPcTransport ::= TEXTUAL-CONVENTION
    STATUS        current
    DESCRIPTION
        ""
    SYNTAX        BITS {
        ether(0),
        dce(1),
        fc(2)
    }

CucsSwFcoeEstcEpTransport ::= TEXTUAL-CONVENTION
    STATUS        current
    DESCRIPTION
        ""
    SYNTAX        BITS {
        ether(0),
        dce(1),
        fc(2)
    }

CucsSwLanBorderType ::= TEXTUAL-CONVENTION
    STATUS        current
    DESCRIPTION
        ""
    SYNTAX        BITS {
        lan(0),
        san(1),
        ipc(2)
    }

CucsSwLanEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsSwLanEpType ::= TEXTUAL-CONVENTION
    STATUS        current
    DESCRIPTION
        ""
    SYNTAX        BITS {
        lan(0),
        san(1),
        ipc(2)
    }

CucsSwLanMonType ::= TEXTUAL-CONVENTION
    STATUS        current
    DESCRIPTION
        ""
    SYNTAX        BITS {
        lan(0),
        san(1),
        ipc(2)
    }

CucsSwLanPcIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsSwLanPcType ::= TEXTUAL-CONVENTION
    STATUS        current
    DESCRIPTION
        ""
    SYNTAX        BITS {
        lan(0),
        san(1),
        ipc(2)
    }

CucsSwMonAdminState ::= TEXTUAL-CONVENTION
    STATUS        current
    DESCRIPTION
        ""
    SYNTAX        INTEGER {
        enabled(1),
        disabled(2)
    }

CucsSwMonDomainLocale ::= TEXTUAL-CONVENTION
    STATUS        current
    DESCRIPTION
        ""
    SYNTAX        BITS {
        server(0),
        chassis(1),
        internal(2),
        external(3)
    }

CucsSwMonLifeCycle ::= TEXTUAL-CONVENTION
    STATUS        current
    DESCRIPTION
        ""
    SYNTAX        INTEGER {
        normal(1),
        new(2),
        deleted(3)
    }

CucsSwMonSrcEpLocale ::= TEXTUAL-CONVENTION
    STATUS        current
    DESCRIPTION
        ""
    SYNTAX        BITS {
        server(0),
        chassis(1),
        internal(2),
        external(3)
    }

CucsSwPIoEpIfType ::= TEXTUAL-CONVENTION
    STATUS        current
    DESCRIPTION
        ""
    SYNTAX        INTEGER {
        unknown(0),
        physical(1),
        aggregation(2),
        virtual(3)
    }

CucsSwSanBorderType ::= TEXTUAL-CONVENTION
    STATUS        current
    DESCRIPTION
        ""
    SYNTAX        BITS {
        lan(0),
        san(1),
        ipc(2)
    }

CucsSwSanEpIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsSwSanEpType ::= TEXTUAL-CONVENTION
    STATUS        current
    DESCRIPTION
        ""
    SYNTAX        BITS {
        lan(0),
        san(1),
        ipc(2)
    }

CucsSwSanMonType ::= TEXTUAL-CONVENTION
    STATUS        current
    DESCRIPTION
        ""
    SYNTAX        BITS {
        lan(0),
        san(1),
        ipc(2)
    }

CucsSwSanPcIfRole ::= TEXTUAL-CONVENTION
    STATUS        current
    DESCRIPTION
        ""
    SYNTAX        INTEGER {
        unknown(0),
        network(1),
        server(2),
        mgmt(3),
        diag(4),
        storage(5),
        monitor(6),
        fcoeStorage(7),
        nasStorage(8)
    }

CucsSwSanPcType ::= TEXTUAL-CONVENTION
    STATUS        current
    DESCRIPTION
        ""
    SYNTAX        BITS {
        lan(0),
        san(1),
        ipc(2)
    }

CucsSwSystemStatsThresholded ::= TEXTUAL-CONVENTION
    STATUS        current
    DESCRIPTION
        ""
    SYNTAX        BITS {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CucsSwSystemStatsHistThresholded ::= TEXTUAL-CONVENTION
    STATUS        current
    DESCRIPTION
        ""
    SYNTAX        BITS {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CucsSwTargetEpType ::= TEXTUAL-CONVENTION
    STATUS        current
    DESCRIPTION
        ""
    SYNTAX        BITS {
        lan(0),
        san(1),
        ipc(2)
    }

CucsSwUlanPurpose ::= TEXTUAL-CONVENTION
    STATUS        current
    DESCRIPTION
        ""
    SYNTAX        INTEGER {
        management(1),
        boot(2),
        reserved1(3),
        reserved2(4)
    }

CucsSwUtilityDomainLocale ::= TEXTUAL-CONVENTION
    STATUS        current
    DESCRIPTION
        ""
    SYNTAX        BITS {
        server(0),
        chassis(1),
        internal(2),
        external(3)
    }

CucsSwUtilityDomainType ::= TEXTUAL-CONVENTION
    STATUS        current
    DESCRIPTION
        ""
    SYNTAX        BITS {
        lan(0),
        san(1),
        ipc(2)
    }

CucsSwUtilityDomainFsmTaskItem ::= TEXTUAL-CONVENTION
    STATUS        current
    DESCRIPTION
        ""
    SYNTAX        INTEGER {
        nop(0),
        deploy(228)
    }

CucsSwVlanPortNsAllocStatus ::= TEXTUAL-CONVENTION
    STATUS        current
    DESCRIPTION
        ""
    SYNTAX        INTEGER {
        available(0),
        exceeded(1)
    }

CucsSysdebugAutoCoreFileExportTargetProto ::= TEXTUAL-CONVENTION
    STATUS        current
    DESCRIPTION
        ""
    SYNTAX        INTEGER {
        none(0),
        ftp(1),
        tftp(2),
        scp(3),
        http(4),
        sftp(5)
    }

CucsSysdebugAutoCoreFileExportTargetFsmTaskItem ::= TEXTUAL-CONVENTION
    STATUS        current
    DESCRIPTION
        ""
    SYNTAX        INTEGER {
        nop(0),
        configure(216)
    }

CucsSysdebugBackupBehaviorInterval ::= TEXTUAL-CONVENTION
    STATUS        current
    DESCRIPTION
        ""
    SYNTAX        INTEGER {
        never(0),
        n1hour(3600),
        n2hours(7200),
        n4hours(14400),
        n8hours(28800),
        n24hours(86400)
    }

CucsSysdebugBackupBehaviorProto ::= TEXTUAL-CONVENTION
    STATUS        current
    DESCRIPTION
        ""
    SYNTAX        INTEGER {
        none(0),
        ftp(1),
        tftp(2),
        scp(3),
        http(4),
        sftp(5)
    }

CucsSysdebugBackupFormat ::= TEXTUAL-CONVENTION
    STATUS        current
    DESCRIPTION
        ""
    SYNTAX        INTEGER {
        ascii(1),
        binary(2)
    }

CucsSysdebugCoreExportStatus ::= TEXTUAL-CONVENTION
    STATUS        current
    DESCRIPTION
        ""
    SYNTAX        INTEGER {
        success(1),
        failure(2)
    }

CucsSysdebugCoreFileAdminState ::= TEXTUAL-CONVENTION
    STATUS        current
    DESCRIPTION
        ""
    SYNTAX        INTEGER {
        init(0),
        prepareDownload(1),
        downloaded(2)
    }

CucsSysdebugCoreFileOperState ::= TEXTUAL-CONVENTION
    STATUS        current
    DESCRIPTION
        ""
    SYNTAX        INTEGER {
        unavailable(0),
        available(1),
        availableOnSubordinate(2),
        inProgress(3),
        failed(4)
    }

CucsSysdebugCoreFsmTaskItem ::= TEXTUAL-CONVENTION
    STATUS        current
    DESCRIPTION
        ""
    SYNTAX        INTEGER {
        nop(0),
        download(1041)
    }

CucsSysdebugEpLogAdminState ::= TEXTUAL-CONVENTION
    STATUS        current
    DESCRIPTION
        ""
    SYNTAX        INTEGER {
        policy(0),
        backup(1),
        clear(2)
    }

CucsSysdebugEpLogBackupAction ::= TEXTUAL-CONVENTION
    STATUS        current
    DESCRIPTION
        ""
    SYNTAX        BITS {
        logFull(0),
        onClear(1),
        timer(2),
        onAssocChange(3)
    }

CucsSysdebugEpLogCapacity ::= TEXTUAL-CONVENTION
    STATUS        current
    DESCRIPTION
        ""
    SYNTAX        INTEGER {
        unknown(0),
        available(1),
        low(2),
        veryLow(3),
        full(4)
    }

CucsSysdebugEpLogType ::= TEXTUAL-CONVENTION
    STATUS        current
    DESCRIPTION
        ""
    SYNTAX        INTEGER {
        sel(1),
        obfl(2),
        syslog(3)
    }

CucsSysdebugLogControlDomainEnum ::= TEXTUAL-CONVENTION
    STATUS        current
    DESCRIPTION
        ""
    SYNTAX        INTEGER {
        sysmgmt(0)
    }

CucsSysdebugLogControlEpFsmTaskItem ::= TEXTUAL-CONVENTION
    STATUS        current
    DESCRIPTION
        ""
    SYNTAX        INTEGER {
        nop(0),
        logControlPersist(219)
    }

CucsSysdebugLogControlLevel ::= TEXTUAL-CONVENTION
    STATUS        current
    DESCRIPTION
        ""
    SYNTAX        INTEGER {
        debug0(0),
        debug1(1),
        debug2(2),
        debug3(3),
        debug4(4),
        info(5),
        warn(6),
        minor(7),
        major(8),
        crit(9)
    }

CucsSysdebugMEpLogOperState ::= TEXTUAL-CONVENTION
    STATUS        current
    DESCRIPTION
        ""
    SYNTAX        INTEGER {
        ok(0),
        permissionDeniedError(1),
        remoteCommunicationError(2),
        bmcCommunicationError(3),
        internalUcsmError(4)
    }

CucsSysdebugManualCoreFileExportTargetAdminState ::= TEXTUAL-CONVENTION
    STATUS        current
    DESCRIPTION
        ""
    SYNTAX        INTEGER {
        enabled(1),
        disabled(2)
    }

CucsSysdebugManualCoreFileExportTargetProto ::= TEXTUAL-CONVENTION
    STATUS        current
    DESCRIPTION
        ""
    SYNTAX        INTEGER {
        none(0),
        ftp(1),
        tftp(2),
        scp(3),
        http(4),
        sftp(5)
    }

CucsSysdebugManualCoreFileExportTargetFsmTaskItem ::= TEXTUAL-CONVENTION
    STATUS        current
    DESCRIPTION
        ""
    SYNTAX        INTEGER {
        nop(0),
        export(214)
    }

CucsSysdebugTSCmdOptMajorType ::= TEXTUAL-CONVENTION
    STATUS        current
    DESCRIPTION
        ""
    SYNTAX        INTEGER {
        chassis(0),
        fex(1),
        server(2),
        ucsm(3)
    }

CucsSysdebugTechSupportAdminState ::= TEXTUAL-CONVENTION
    STATUS        current
    DESCRIPTION
        ""
    SYNTAX        INTEGER {
        init(0),
        start(1),
        created(2),
        prepareDownload(3),
        delete(4)
    }

CucsSysdebugTechSupportFsmTaskItem ::= TEXTUAL-CONVENTION
    STATUS        current
    DESCRIPTION
        ""
    SYNTAX        INTEGER {
        nop(0),
        initiate(881),
        deleteTechSupFile(883),
        download(886)
    }

CucsSysdebugTechSupportOperState ::= TEXTUAL-CONVENTION
    STATUS        current
    DESCRIPTION
        ""
    SYNTAX        INTEGER {
        unavailable(0),
        available(1),
        availableOnSubordinate(2),
        inProgress(3),
        failed(4)
    }

CucsSysfileExporterPostAction ::= TEXTUAL-CONVENTION
    STATUS        current
    DESCRIPTION
        ""
    SYNTAX        INTEGER {
        none(0),
        remove(1)
    }

CucsSysfileMutationAction ::= TEXTUAL-CONVENTION
    STATUS        current
    DESCRIPTION
        ""
    SYNTAX        INTEGER {
        none(0),
        remove(1)
    }

CucsSysfileMutationFsmTaskItem ::= TEXTUAL-CONVENTION
    STATUS        current
    DESCRIPTION
        ""
    SYNTAX        INTEGER {
        nop(0),
        single(209),
        global(211)
    }

CucsTopMode ::= TEXTUAL-CONVENTION
    STATUS        current
    DESCRIPTION
        ""
    SYNTAX        INTEGER {
        unspecified(0),
        standAlone(1),
        cluster(2)
    }

CucsTrigAckMode ::= TEXTUAL-CONVENTION
    STATUS        current
    DESCRIPTION
        ""
    SYNTAX        INTEGER {
        immediate(0),
        userAck(1),
        timerAutomatic(2)
    }

CucsTrigAckOperState ::= TEXTUAL-CONVENTION
    STATUS        current
    DESCRIPTION
        ""
    SYNTAX        INTEGER {
        untriggered(0),
        evaluationPending(1),
        evaluated(2),
        waitingForUser(3),
        waitingForMaintWindow(4),
        applyPending(5)
    }

CucsTrigAdminState ::= TEXTUAL-CONVENTION
    STATUS        current
    DESCRIPTION
        ""
    SYNTAX        INTEGER {
        triggerImmediate(0),
        triggered(1),
        untriggered(2)
    }

CucsTrigDay ::= TEXTUAL-CONVENTION
    STATUS        current
    DESCRIPTION
        ""
    SYNTAX        INTEGER {
        monday(1),
        tuesday(2),
        wednesday(3),
        thursday(4),
        friday(5),
        saturday(6),
        sunday(7),
        oddDay(8),
        evenDay(9),
        everyDay(10)
    }

CucsTrigOperState ::= TEXTUAL-CONVENTION
    STATUS        current
    DESCRIPTION
        ""
    SYNTAX        INTEGER {
        pending(0),
        inProgress(1),
        failed(2),
        triggered(3),
        capReached(4)
    }

CucsTrigTriggeredState ::= TEXTUAL-CONVENTION
    STATUS        current
    DESCRIPTION
        ""
    SYNTAX        INTEGER {
        pending(0),
        inProgress(1),
        failed(2),
        triggered(3)
    }

CucsVmAdaptorOwner ::= TEXTUAL-CONVENTION
    STATUS        current
    DESCRIPTION
        ""
    SYNTAX        INTEGER {
        unknown(0),
        physical(1),
        policy(2),
        logical(4)
    }

CucsVmHbaType ::= TEXTUAL-CONVENTION
    STATUS        current
    DESCRIPTION
        ""
    SYNTAX        INTEGER {
        unknown(0),
        ether(1),
        fc(4),
        scsi(8),
        ipc(16)
    }

CucsVmNicType ::= TEXTUAL-CONVENTION
    STATUS        current
    DESCRIPTION
        ""
    SYNTAX        INTEGER {
        unknown(0),
        ether(1),
        fc(4),
        scsi(8),
        ipc(16)
    }

CucsVmStatus ::= TEXTUAL-CONVENTION
    STATUS        current
    DESCRIPTION
        ""
    SYNTAX        INTEGER {
        unknown(0),
        online(1),
        offline(2)
    }

CucsVmSwitchAdminState ::= TEXTUAL-CONVENTION
    STATUS        current
    DESCRIPTION
        ""
    SYNTAX        INTEGER {
        disable(0),
        enable(1)
    }

CucsVnicAEtherIfType ::= TEXTUAL-CONVENTION
    STATUS        current
    DESCRIPTION
        ""
    SYNTAX        INTEGER {
        unknown(0),
        ether(1),
        fc(4),
        scsi(8),
        ipc(16)
    }

CucsVnicAFcIfType ::= TEXTUAL-CONVENTION
    STATUS        current
    DESCRIPTION
        ""
    SYNTAX        INTEGER {
        unknown(0),
        ether(1),
        fc(4),
        scsi(8),
        ipc(16)
    }

CucsVnicAIpcIfType ::= TEXTUAL-CONVENTION
    STATUS        current
    DESCRIPTION
        ""
    SYNTAX        INTEGER {
        unknown(0),
        ether(1),
        fc(4),
        scsi(8),
        ipc(16)
    }

CucsVnicAScsiIfType ::= TEXTUAL-CONVENTION
    STATUS        current
    DESCRIPTION
        ""
    SYNTAX        INTEGER {
        unknown(0),
        ether(1),
        fc(4),
        scsi(8),
        ipc(16)
    }

CucsVnicConnectionOwner ::= TEXTUAL-CONVENTION
    STATUS        current
    DESCRIPTION
        ""
    SYNTAX        INTEGER {
        unknown(0),
        physical(1),
        policy(2),
        logical(4)
    }

CucsVnicConnectionType ::= TEXTUAL-CONVENTION
    STATUS        current
    DESCRIPTION
        ""
    SYNTAX        INTEGER {
        unknown(0),
        ether(1),
        fc(4),
        scsi(8),
        ipc(16)
    }

CucsVnicDefBehType ::= TEXTUAL-CONVENTION
    STATUS        current
    DESCRIPTION
        ""
    SYNTAX        INTEGER {
        vnic(1),
        vhba(2)
    }

CucsVnicDefaultAction ::= TEXTUAL-CONVENTION
    STATUS        current
    DESCRIPTION
        ""
    SYNTAX        INTEGER {
        none(0),
        hwInherit(1)
    }

CucsVnicDynamicConReqProtection ::= TEXTUAL-CONVENTION
    STATUS        current
    DESCRIPTION
        ""
    SYNTAX        INTEGER {
        none(0)
    }

CucsVnicEtherType ::= TEXTUAL-CONVENTION
    STATUS        current
    DESCRIPTION
        ""
    SYNTAX        INTEGER {
        unknown(0),
        ether(1),
        fc(4),
        scsi(8),
        ipc(16)
    }

CucsVnicEtherBaseSwitchId ::= TEXTUAL-CONVENTION
    STATUS        current
    DESCRIPTION
        ""
    SYNTAX        INTEGER {
        none(0),
        a(1),
        b(2),
        aB(5),
        bA(6)
    }

CucsVnicExternalMgmtIPMode ::= TEXTUAL-CONVENTION
    STATUS        current
    DESCRIPTION
        ""
    SYNTAX        INTEGER {
        none(1),
        static(2),
        pooled(3)
    }

CucsVnicFcBasePersBind ::= TEXTUAL-CONVENTION
    STATUS        current
    DESCRIPTION
        ""
    SYNTAX        INTEGER {
        disabled(0),
        enabled(4)
    }

CucsVnicFcBaseType ::= TEXTUAL-CONVENTION
    STATUS        current
    DESCRIPTION
        ""
    SYNTAX        INTEGER {
        unknown(0),
        ether(1),
        fc(4),
        scsi(8),
        ipc(16)
    }

CucsVnicHostNwIOPerfPref ::= TEXTUAL-CONVENTION
    STATUS        current
    DESCRIPTION
        ""
    SYNTAX        INTEGER {
        none(0),
        highPerfReqd(1)
    }

CucsVnicIPv4DnsPref ::= TEXTUAL-CONVENTION
    STATUS        current
    DESCRIPTION
        ""
    SYNTAX        INTEGER {
        preferred(0),
        alternate(1)
    }

CucsVnicIfOperState ::= TEXTUAL-CONVENTION
    STATUS        current
    DESCRIPTION
        ""
    SYNTAX        INTEGER {
        indeterminate(0),
        up(1),
        down(2),
        failed(4)
    }

CucsVnicInstantiation ::= TEXTUAL-CONVENTION
    STATUS        current
    DESCRIPTION
        ""
    SYNTAX        INTEGER {
        manual(0),
        default(1),
        dynamic(2)
    }

CucsVnicIpcType ::= TEXTUAL-CONVENTION
    STATUS        current
    DESCRIPTION
        ""
    SYNTAX        INTEGER {
        unknown(0),
        ether(1),
        fc(4),
        scsi(8),
        ipc(16)
    }

CucsVnicL2IfSwitchId ::= TEXTUAL-CONVENTION
    STATUS        current
    DESCRIPTION
        ""
    SYNTAX        INTEGER {
        none(0),
        a(1),
        b(2),
        aB(5),
        bA(6)
    }

CucsVnicLanConnTemplSwitchId ::= TEXTUAL-CONVENTION
    STATUS        current
    DESCRIPTION
        ""
    SYNTAX        INTEGER {
        none(0),
        a(1),
        b(2),
        aB(5),
        bA(6)
    }

CucsVnicProfileSetFsmTaskItem ::= TEXTUAL-CONVENTION
    STATUS        current
    DESCRIPTION
        ""
    SYNTAX        INTEGER {
        nop(0),
        deploy(187)
    }

CucsVnicSanConnTemplTarget ::= TEXTUAL-CONVENTION
    STATUS        current
    DESCRIPTION
        ""
    SYNTAX        BITS {
        vm(0),
        adaptor(1)
    }

CucsVnicScsiType ::= TEXTUAL-CONVENTION
    STATUS        current
    DESCRIPTION
        ""
    SYNTAX        INTEGER {
        unknown(0),
        ether(1),
        fc(4),
        scsi(8),
        ipc(16)
    }

CucsVnicTemplateTarget ::= TEXTUAL-CONVENTION
    STATUS        current
    DESCRIPTION
        ""
    SYNTAX        BITS {
        vm(0),
        adaptor(1)
    }

CucsVnicTemplateType ::= TEXTUAL-CONVENTION
    STATUS        current
    DESCRIPTION
        ""
    SYNTAX        INTEGER {
        initialTemplate(1),
        updatingTemplate(2)
    }

CucsVnicVnicBootDev ::= TEXTUAL-CONVENTION
    STATUS        current
    DESCRIPTION
        ""
    SYNTAX        INTEGER {
        disabled(0),
        enabled(1)
    }

END
