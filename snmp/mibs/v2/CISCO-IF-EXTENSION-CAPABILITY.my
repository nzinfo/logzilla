-- *****************************************************************
-- CISCO-IF-EXTENSION-CAPABILITY.my:
-- Cisco CISCO-IF-EXTENSION-MIB AGENT-CAPABILITIES
--
-- Jan 2004, Liwei Lue 
--
-- Copyright (c) 2004, 2005 by Cisco Systems, Inc.
-- All rights reserved.
-- *****************************************************************

CISCO-IF-EXTENSION-CAPABILITY DEFINITIONS ::= BEGIN

IMPORTS
        MODULE-IDENTITY
                FROM SNMPv2-SMI
        AGENT-CAPABILITIES
                FROM SNMPv2-CONF
        ciscoAgentCapability
                FROM CISCO-SMI;

ciscoIfExtensionCapability MODULE-IDENTITY
        LAST-UPDATED    "200602210000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"

        DESCRIPTION
                "The capabilities description of 
                 CISCO-IF-EXTENSION-MIB."
        REVISION        "200602210000Z"
        DESCRIPTION
                "Added capability statement 
                 ciscoIfExtCapabilityACSWV03R000 for 
                 Application Control Engine (ACE)."
        REVISION        "200504140000Z"
        DESCRIPTION
                "Added capability statement 
                 ciscoIfExtCapSanOSV30R1MDS9000."
        REVISION        "200503040000Z"
        DESCRIPTION
                "Added capability statement 
                 ciscoIfExtCapV12R0217bSXAPCat6K."
        REVISION        "200401260000Z"
        DESCRIPTION
                "Initial version of this MIB module."
        ::= { ciscoAgentCapability 395 }

ciscoIfExtensionCapV08R0301 AGENT-CAPABILITIES
    PRODUCT-RELEASE     "Cisco CatOS 8.3(1) on Catalyst 6000/6500 and
                         Cisco 7600 series devices."
    STATUS              current
    DESCRIPTION         "CISCO-IF-EXTENSION-MIB capabilities."

    SUPPORTS            CISCO-IF-EXTENSION-MIB
        INCLUDES        { ciscoIfExtDot1qEtherTypeGroup,
                          ciscoIfExtUtilizationGroup,
                          ciscoIfExtDot1dBaseMappingGroup 
                        }
    ::= { ciscoIfExtensionCapability 1 }

ciscoIfExtCapV12R0217bSXAPCat6K AGENT-CAPABILITIES
    PRODUCT-RELEASE     "Cisco IOS 12.2(17b)SXA on Catalyst 6000/6500
                        and Cisco 7600 series devices."
    STATUS              current
    DESCRIPTION         "CISCO-IF-EXTENSION-MIB capabilities."

    SUPPORTS            CISCO-IF-EXTENSION-MIB
        INCLUDES        { ciscoIfExtensionTablePacketGroup,
                          ciscoIfExtensionTableIntfGroup,
                          ciscoIfExtDot1qEtherTypeGroup,
                          ciscoIfExtDot1dBaseMappingGroup
                        }
    ::= { ciscoIfExtensionCapability 2 }

ciscoIfExtCapSanOSV30R1MDS9000 AGENT-CAPABILITIES
    PRODUCT-RELEASE      "Cisco SanOS 3.0 on Cisco MDS 9000
                          series devices."
    STATUS          current
    DESCRIPTION     "CISCO-IF-EXTENSION-MIB capabilities."
    SUPPORTS        CISCO-IF-EXTENSION-MIB
    INCLUDES        {
                        ciscoIfExtensionTableIntfGroup2,
                        ciscoIfExtUtilizationGroup,
                        ciscoIfExtDot1dBaseMappingGroup,
                        ciscoIfExtIfNameMappingGroup,
                        cieIfStatusListGroup 
                    }
        VARIATION   cieIfDhcpMode
            SYNTAX  INTEGER{ false(2) }
            ACCESS  read-only
            DESCRIPTION
                    "Implementation supports only read-only access for 
                     this object. Support for true(1) is only required
                    on interfaces which support DHCP."

        VARIATION   cieIfMtu
            ACCESS  read-only
            DESCRIPTION
                    "Implementation support only read-only access for 
                     this object."
    ::= { ciscoIfExtensionCapability 3 }
ciscoIfExtCapabilityACSWV03R000 AGENT-CAPABILITIES
    PRODUCT-RELEASE "ACSW (Application Control Software) 3.0"
    STATUS          current
    DESCRIPTION     "CISCO-IF-EXTENSION-MIB capabilities."
    SUPPORTS        CISCO-IF-EXTENSION-MIB
    INCLUDES        { ciscoIfExtIfNameMappingGroup }
    ::= { ciscoIfExtensionCapability 4 }
END
