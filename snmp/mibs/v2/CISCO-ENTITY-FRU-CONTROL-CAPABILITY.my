-- *****************************************************************
--
-- AGENT-CAPABILITIES mib for CISCO-ENTITY-FRU-CONTROL-MIB
--
-- March 2002, Subra Hegde, Sirisha Paturi
-- August 2003, Wen Xu
-- September 2003, Wen Xu
-- Janurary 2004, Wen Xu
-- September 2004, Jaikumar Chidambaram
-- March 2005, Bala Kanchana
--
-- Copyright(c) 2002, 2003, 2004, 2005, 2006 by Cisco Systems,Inc.
--
-- *****************************************************************


CISCO-ENTITY-FRU-CONTROL-CAPABILITY DEFINITIONS ::= BEGIN
IMPORTS
        MODULE-IDENTITY
                FROM SNMPv2-SMI
        AGENT-CAPABILITIES
                FROM SNMPv2-CONF
        ciscoAgentCapability
                FROM CISCO-SMI;

ciscoEntityFruControlCapability MODULE-IDENTITY
        LAST-UPDATED    "200604190000Z"
        ORGANIZATION    "Cisco Systems, Inc."
        CONTACT-INFO
                "       Cisco Systems
                        Customer Service

                Postal: 170 W Tasman Drive
                        San Jose, CA  95134
                        USA

                        Tel: +1 800 553-NETS

                E-mail: cs-snmp@cisco.com
                        cs-lan-switch-snmp@cisco.com "
        DESCRIPTION
                "The Agent Capabilities for
                CISCO-ENTITY-FRU-CONTROL-MIB."
        REVISION        "200604190000Z"
        DESCRIPTION
            "- Added Agent capabilities 
               ciscoEfcCapACSWV03R000 for Cisco 
               Application Control Engine (ACE)."
        REVISION        "200603160000Z"
        DESCRIPTION
            "- Add VARIATIONs for notifications 
               cefcModuleStatusChange, 
               cefcPowerStatusChange, 
               cefcFRUInserted and cefcFRURemoved 
               in ciscoEfcCapabilityCatOSV08R0101, 
               ciscoEfcCapabilityCatOSV08R0301 
               and ciscoEfcCapCatOSV08R0501."
        REVISION "200601310000Z"
        DESCRIPTION
            "- Added ciscoEfcCapSanOSV21R1MDS9000 for 
               SAN OS 2.1(1) on MDS 9000 series devices. 
            - Added ciscoEfcCapSanOSV30R1MDS9000 for 
               SAN OS 3.0(1) on MDS 9000 series devices." 
        REVISION "200507120000Z"
        DESCRIPTION
            "- Added ciscoEfcCapCatOSV08R0501."
        REVISION "200503090000Z"
        DESCRIPTION
            "- Added capabilities ciscoEfcCapV12R04TP26XX
               ciscoEfcCapV12R04TP28XX, ciscoEfcCapV12R04TP3725,
               ciscoEfcCapV12R04TP3745, ciscoEfcCapV12R04TP3825,
               ciscoEfcCapV12R04TP3845, ciscoEfcCapV12R04TPIAD243X,
               ciscoEfcCapV12R04TPVG224 for IOS 12.4T on platforms
               26xx, 28xx, 37xx, 38xx, IAD243x, VG224"
        REVISION "200409150000Z"
        DESCRIPTION
            "- Added ciscoEfcCapabilityV12R03P5XXX for IOS 12.3
               on Access Server Platforms (AS5350, AS5400 and
               AS5850)."
        REVISION "200401150000Z"
        DESCRIPTION
            "- Added ciscoEfcCapV12RO217bSXACat6K.
             - Added ciscoEfcCapabilityCatOSV08R0301."
        REVISION "200309150000Z"
        DESCRIPTION
            "- Added ciscoEfcCapabilityV12R0119ECat6K for IOS
               12.1(19E) on Catalyst 6000/6500 and Cisco
               7600 series devices.
             - Added ciscoEfcCapabilityV12RO217SXCat6K for IOS
               12.2(17SX) on Catalyst 6000/6500 and Cisco
               7600 series devices.
             - Added ciscoEfcCapabilityCatOSV08R0101 for
               Cisco CatOS 8.1(1)."
        REVISION "200203200000Z"
        DESCRIPTION
            "Initial version of the MIB Module.
             - The ciscoEntityFruControlCapabilityV2R00 is
               for MGX8850 and BPX SES platform.
             - The ciscoEntityFRUControlCapabilityV12R00SGSR
               is for GSR platform."
        ::= { ciscoAgentCapability 264 }

ciscoEntityFruControlCapabilityV2R00 AGENT-CAPABILITIES
    PRODUCT-RELEASE      "MGX8850 Release 2.00,
                          BPX SES Release 1.00"
    STATUS               current
    DESCRIPTION          "CISCO-ENTITY-FRU-CONTROL-MIB Capabilities"

    SUPPORTS CISCO-ENTITY-FRU-CONTROL-MIB
        INCLUDES { cefcMIBModuleGroup }

        VARIATION cefcModuleAdminStatus
        ACCESS    read-only
        DESCRIPTION "Write access is not supported."

    ::= { ciscoEntityFruControlCapability 1 }

ciscoEntityFRUControlCapabilityV12R00SGSR AGENT-CAPABILITIES

    PRODUCT-RELEASE "Cisco IOS 12.0S for GSR"
    STATUS          current
    DESCRIPTION     "CISCO-ENTITY-FRU-CONTROL-MIB capabilities
                    for GSR platform."

    SUPPORTS        CISCO-ENTITY-FRU-CONTROL-MIB
    INCLUDES        {
                      cefcMIBModuleGroup,
                      cefcMIBNotificationEnablesGroup,
                      cefcMgmtNotificationsGroup
                    }

    VARIATION       cefcModuleAdminStatus
    ACCESS          read-only
    DESCRIPTION     "Write not implemented"

    VARIATION       cefcModuleStatusChange  -- NOTIFICATION-TYPE
--              OBJECTS { cefcModuleOperStatus,
--                        cefcModuleStatusLastChangeTime,
--                        entPhysicalDescr,
--                        entPhysicalName }
    DESCRIPTION
        "This notification is generated when the value of
        cefcModuleOperStatus changes. It can be utilized by
        an NMS to update the status of the module it is
        managing. The varbind for this notification indicates
        the entPhysicalDescr and entPhysicalName of the
        module, the operational-status of the module and the
        value of sysUpTime at the time the
        cefcModuleOperStatus is changed."

    VARIATION       cefcPowerStatusChange  -- NOTIFICATION-TYPE
    ACCESS          not-implemented
    DESCRIPTION     "Not Supported"

    VARIATION       cefcFRUInserted  -- NOTIFICATION-TYPE
--              OBJECTS { entPhysicalContainedIn,
--                        entPhysicalDescr,
--                        entPhysicalName }
    DESCRIPTION

        "The cefcFRUInserted notification indicates that a FRU
        was inserted. The varbind for this notification
        indicates the entPhysicalDescr and entPhysicalName of
        the inserted FRU, and the entPhysicalIndex of the
        FRU's container."

    VARIATION       cefcFRURemoved  -- NOTIFICATION-TYPE
--              OBJECTS { entPhysicalContainedIn,
--                        entPhysicalDescr,
--                        entPhysicalName }
    DESCRIPTION
        "The cefcFRURemoved notification indicates that a FRU
        was removed. The varbind for this notification
        indicates the entPhysicalDescr and entPhysicalName of
        the removed FRU, and the entPhysicalIndex of the FRU's
        container."

    ::= { ciscoEntityFruControlCapability 2 }

ciscoEfcCapabilityV12R0119ECat6K AGENT-CAPABILITIES
    PRODUCT-RELEASE  "Cisco IOS 12.1(19E) on Catalyst 6000/6500
                      and Cisco 7600 series devices."
    STATUS            current
    DESCRIPTION       "CISCO-ENTITY-FRU-CONTROL-MIB capabilities."

    SUPPORTS           CISCO-ENTITY-FRU-CONTROL-MIB
        INCLUDES           {
                               cefcMIBPowerModeGroup,
                               cefcMIBPowerFRUControlGroup,
                               cefcMIBModuleGroup,
                               cefcMIBNotificationEnablesGroup,
                               cefcMgmtNotificationsGroup,
                               cefcMIBInLinePowerControlGroup
                           }

        VARIATION              cefcMaxDefaultInLinePower
        ACCESS                 read-only
        DESCRIPTION            "write access is not supported."

    ::= { ciscoEntityFruControlCapability 3 }


ciscoEfcCapabilityV12RO217SXCat6K AGENT-CAPABILITIES
    PRODUCT-RELEASE  "Cisco IOS 12.2(17SX) on Catalyst 6000/6500
                      and Cisco 7600 series devices."
    STATUS            current
    DESCRIPTION       "CISCO-ENTITY-FRU-CONTROL-MIB capabilities."

    SUPPORTS           CISCO-ENTITY-FRU-CONTROL-MIB
        INCLUDES           {
                               cefcMIBPowerModeGroup,
                               cefcMIBPowerFRUControlGroup,
                               cefcMIBModuleGroup,
                               cefcMIBNotificationEnablesGroup,
                               cefcMgmtNotificationsGroup,
                               cefcMIBPowerOperModeGroup,
                               cefcMIBInLinePowerControlGroup,
                               cefcMIBInLinePowerControlGroupRev1
                           }

        VARIATION              cefcPowerRedundancyOperMode
        SYNTAX                 INTEGER { redundant(2), combined(3) }
        DESCRIPTION            "notsupported(1) is not supported."

        VARIATION              cefcMaxDefaultInLinePower
        ACCESS                 read-only
        DESCRIPTION            "write access is not supported."

        VARIATION              cefcMaxDefaultHighInLinePower
        ACCESS                 read-only
        DESCRIPTION            "write access is not supported."

    ::= { ciscoEntityFruControlCapability 4 }

ciscoEfcCapabilityCatOSV08R0101 AGENT-CAPABILITIES
    PRODUCT-RELEASE  "Cisco CatOS 8.1(1)."
    STATUS            current
    DESCRIPTION      "CISCO-ENTITY-FRU-CONTROL-MIB capabilities."

    SUPPORTS           CISCO-ENTITY-FRU-CONTROL-MIB
        INCLUDES           {
                               cefcMIBPowerModeGroup,
                               cefcMIBPowerFRUControlGroup,
                               cefcMIBModuleGroup,
                               cefcMIBNotificationEnablesGroup,
                               cefcMgmtNotificationsGroup,
                               cefcMIBInLinePowerControlGroup
                           }

        VARIATION        cefcModuleStatusChange -- NOTIFICATION-TYPE
--          OBJECTS       { cefcModuleOperStatus,
--                          cefcModuleStatusLastChangeTime,
--                          entPhysicalDescr,
--                          entPhysicalName 
--                        }
            DESCRIPTION
                    "In addition to the regular varbinds, the instance 
                     values of entPhysicalDescr and entPhysicalName are 
                     appended to the notification."

        VARIATION        cefcPowerStatusChange -- NOTIFICATION-TYPE
--          OBJECTS       { cefcFRUPowerOperStatus,
--                          cefcFRUPowerAdminStatus,
--                          entPhysicalDescr,
--                          entPhysicalName 
--                        }
            DESCRIPTION
                    "In addition to the regular varbinds, the instance 
                     values of entPhysicalDescr and entPhysicalName are 
                     appended to the notification."

        VARIATION        cefcFRUInserted -- NOTIFICATION-TYPE
--          OBJECTS       { entPhysicalContainedIn,
--                          entPhysicalDescr,
--                          entPhysicalName
--                        }
            DESCRIPTION
                    "In addition to the regular varbinds, the instance 
                     values of entPhysicalDescr and entPhysicalName are 
                     appended to the notification."

        VARIATION        cefcFRURemoved -- NOTIFICATION-TYPE
--          OBJECTS       { entPhysicalContainedIn,
--                          entPhysicalDescr,
--                          entPhysicalName
--                        }
            DESCRIPTION
                    "In addition to the regular varbinds, the instance 
                     values of entPhysicalDescr and entPhysicalName are 
                     appended to the notification."

    ::= { ciscoEntityFruControlCapability 5 }

ciscoEfcCapV12RO217bSXACat6K AGENT-CAPABILITIES
    PRODUCT-RELEASE  "Cisco IOS 12.2(17b)SXA on Catalyst 6000/6500
                      and Cisco 7600 series devices."
    STATUS            current
    DESCRIPTION       "CISCO-ENTITY-FRU-CONTROL-MIB capabilities."

    SUPPORTS           CISCO-ENTITY-FRU-CONTROL-MIB
        INCLUDES           {
                               cefcMIBPowerModeGroup,
                               cefcMIBPowerFRUControlGroup,
                               cefcMIBModuleGroup,
                               cefcMIBNotificationEnablesGroup,
                               cefcMgmtNotificationsGroup,
                               cefcMIBPowerOperModeGroup,
                               cefcMIBInLinePowerControlGroup,
                               cefcMIBInLinePowerControlGroupRev1,
                               cefcIntelliModuleGroup
                           }

        VARIATION              cefcPowerRedundancyOperMode
        SYNTAX                 INTEGER { redundant(2), combined(3) }
        DESCRIPTION            "notsupported(1) is not supported."

        VARIATION              cefcMaxDefaultInLinePower
        ACCESS                 read-only
        DESCRIPTION            "write access is not supported."

        VARIATION              cefcMaxDefaultHighInLinePower
        ACCESS                 read-only
        DESCRIPTION            "write access is not supported."

    ::= { ciscoEntityFruControlCapability 6 }

ciscoEfcCapabilityCatOSV08R0301 AGENT-CAPABILITIES
    PRODUCT-RELEASE  "Cisco CatOS 8.3(1) on Catalyst 6000/6500
                      and Cisco 7600 series devices."
    STATUS            current
    DESCRIPTION      "CISCO-ENTITY-FRU-CONTROL-MIB capabilities."

    SUPPORTS           CISCO-ENTITY-FRU-CONTROL-MIB
        INCLUDES           {
                               cefcMIBPowerModeGroup,
                               cefcMIBPowerFRUControlGroup,
                               cefcMIBModuleGroup,
                               cefcMIBNotificationEnablesGroup,
                               cefcMgmtNotificationsGroup,
                               cefcMIBInLinePowerControlGroup,
                               cefcIntelliModuleGroup
                           }

        VARIATION        cefcModuleStatusChange -- NOTIFICATION-TYPE
--          OBJECTS       { cefcModuleOperStatus,
--                          cefcModuleStatusLastChangeTime,
--                          entPhysicalDescr,
--                          entPhysicalName 
--                        }
            DESCRIPTION
                    "In addition to the regular varbinds, the instance 
                     values of entPhysicalDescr and entPhysicalName are 
                     appended to the notification."

        VARIATION        cefcPowerStatusChange -- NOTIFICATION-TYPE
--          OBJECTS       { cefcFRUPowerOperStatus,
--                          cefcFRUPowerAdminStatus,
--                          entPhysicalDescr,
--                          entPhysicalName 
--                        }
            DESCRIPTION
                    "In addition to the regular varbinds, the instance 
                     values of entPhysicalDescr and entPhysicalName are 
                     appended to the notification."

        VARIATION        cefcFRUInserted -- NOTIFICATION-TYPE
--          OBJECTS       { entPhysicalContainedIn,
--                          entPhysicalDescr,
--                          entPhysicalName
--                        }
            DESCRIPTION
                    "In addition to the regular varbinds, the instance 
                     values of entPhysicalDescr and entPhysicalName are 
                     appended to the notification."

        VARIATION        cefcFRURemoved -- NOTIFICATION-TYPE
--          OBJECTS       { entPhysicalContainedIn,
--                          entPhysicalDescr,
--                          entPhysicalName
--                        }
            DESCRIPTION
                    "In addition to the regular varbinds, the instance 
                     values of entPhysicalDescr and entPhysicalName are 
                     appended to the notification."

    ::= { ciscoEntityFruControlCapability 7 }

ciscoEfcCapabilityV12R03P5XXX AGENT-CAPABILITIES
    PRODUCT-RELEASE  "Cisco IOS 12.3 for Access Server Platforms
                      AS5350, AS5400 and AS5850."
    STATUS            current
    DESCRIPTION      "CISCO-ENTITY-FRU-CONTROL-MIB capabilities."

    SUPPORTS           CISCO-ENTITY-FRU-CONTROL-MIB
        INCLUDES           {
                               cefcMIBPowerFRUControlGroup,
                               cefcMIBModuleGroup,
                               cefcMIBNotificationEnablesGroup,
                               cefcMgmtNotificationsGroup
                           }

        VARIATION      cefcFRUPowerAdminStatus
        ACCESS         read-only
        DESCRIPTION    "write access is not suppported."

        VARIATION      cefcModuleAdminStatus
        ACCESS         read-only
        DESCRIPTION    "write access is not suppported."

    ::= { ciscoEntityFruControlCapability 8 }

ciscoEfcCapV12R04TP3725 AGENT-CAPABILITIES
    PRODUCT-RELEASE  "Cisco IOS 12.4T for c3725 Platform"
    STATUS            current
    DESCRIPTION      "CISCO-ENTITY-FRU-CONTROL-MIB capabilities."

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "Write access is not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported"

        VARIATION      cefcFRURemoved
        ACCESS         not-implemented
        DESCRIPTION    "Online Removal not supported"

        VARIATION      cefcMaxDefaultHighInLinePower
        ACCESS         not-implemented
        DESCRIPTION    "Information not available"

    ::= { ciscoEntityFruControlCapability 9 }

ciscoEfcCapV12R04TP3745 AGENT-CAPABILITIES
    PRODUCT-RELEASE  "Cisco IOS 12.4T for c3745 Platforms"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "write access is not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcMaxDefaultHighInLinePower
        ACCESS         not-implemented
        DESCRIPTION    "Information not available"

    ::= { ciscoEntityFruControlCapability 10 }

ciscoEfcCapV12R04TP26XX AGENT-CAPABILITIES
    PRODUCT-RELEASE  "Cisco IOS 12.4T for c26xx XM Platforms"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "write access is not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported"

        VARIATION      cefcFRURemoved
        ACCESS         not-implemented
        DESCRIPTION    "Online Removal not supported"

        VARIATION      cefcMaxDefaultHighInLinePower
        ACCESS         not-implemented
        DESCRIPTION    "Information not available"


    ::= { ciscoEntityFruControlCapability 11 }

ciscoEfcCapV12R04TPIAD243X AGENT-CAPABILITIES
    PRODUCT-RELEASE  "Cisco IOS 12.4T for IAD 243x Platforms"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "write access not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports enumeration 'on'"

        VARIATION      cefcFRUPowerOperStatus
        SYNTAX         INTEGER { on (2) }
        DESCRIPTION    "Supports enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access not supported"

        VARIATION      cefcModuleStatusLastChangeTime
        SYNTAX         INTEGER (0)
        DESCRIPTION    "Information not available"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcModuleStatusChange
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported in
                        platform IAD243x"

        VARIATION      cefcFRURemoved
        ACCESS         not-implemented
        DESCRIPTION    "Online Removal not supported in
                        platform IAD243x"

        VARIATION      cefcMaxDefaultHighInLinePower
        ACCESS         not-implemented
        DESCRIPTION    "Information not available"

    ::= { ciscoEntityFruControlCapability 12 }

ciscoEfcCapV12R04TPVG224 AGENT-CAPABILITIES
    PRODUCT-RELEASE  "Cisco IOS 12.4T for VG224 Platform"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "write access is not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports enumeration 'on'"

        VARIATION      cefcFRUPowerOperStatus
        SYNTAX         INTEGER { on (2) }
        DESCRIPTION    "Supports enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleStatusLastChangeTime
        SYNTAX         INTEGER (0)
        DESCRIPTION    "Information not available"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcModuleStatusChange
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported"

        VARIATION      cefcFRURemoved
        ACCESS         not-implemented
        DESCRIPTION    "Online Removal not supported"


        VARIATION      cefcMaxDefaultHighInLinePower
        ACCESS         not-implemented
        DESCRIPTION    "Information not available"

    ::= { ciscoEntityFruControlCapability 13 }

ciscoEfcCapV12R04TP2691 AGENT-CAPABILITIES
    PRODUCT-RELEASE  "Cisco IOS 12.4T for c2691 Platform"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }


        VARIATION      cefcPowerRedundancyMode
        ACCESS         read-only
        DESCRIPTION    "write access is not supported"

        VARIATION       cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported"

        VARIATION      cefcFRURemoved
        ACCESS         not-implemented
        DESCRIPTION    "Online Removal not supported"

        VARIATION      cefcMaxDefaultHighInLinePower
        ACCESS         not-implemented
        DESCRIPTION    "Information not available"

    ::= { ciscoEntityFruControlCapability 14 }

ciscoEfcCapV12R04TP28XX AGENT-CAPABILITIES
    PRODUCT-RELEASE  "Cisco IOS 12.4T for c28xx Platforms"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "write access is not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported"

        VARIATION      cefcFRURemoved
        ACCESS         not-implemented
        DESCRIPTION    "Online Removal not supported"

        VARIATION      cefcMaxDefaultHighInLinePower
        ACCESS         not-implemented
        DESCRIPTION    "Information not available"

    ::= { ciscoEntityFruControlCapability 15 }

ciscoEfcCapV12R04TP3825 AGENT-CAPABILITIES
    PRODUCT-RELEASE  "Cisco IOS 12.4T for c3825 Platforms"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }
        VARIATION      cefcPowerRedundancyMode
        ACCESS         read-only
        DESCRIPTION    "write access is not supported"

        VARIATION      cefcPowerUnits
        ACCESS         not-implemented
        DESCRIPTION    "Information not available"

        VARIATION      cefcTotalAvailableCurrent
        ACCESS         not-implemented
        DESCRIPTION    "Information not available"

        VARIATION      cefcTotalDrawnCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent

        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcFRUInserted
        ACCESS         not-implemented
        DESCRIPTION    "Online Insertion not supported"

        VARIATION      cefcFRURemoved
        ACCESS         not-implemented
        DESCRIPTION    "Online Removal not supported"

        VARIATION      cefcMaxDefaultHighInLinePower
        ACCESS         not-implemented
        DESCRIPTION    "Information not available"

    ::= { ciscoEntityFruControlCapability 16 }

ciscoEfcCapV12R04TP3845 AGENT-CAPABILITIES
    PRODUCT-RELEASE  "Cisco IOS 12.4T for c3845 Platform"
    STATUS            current
    DESCRIPTION      "CISCO-ENTITY-FRU-CONTROL-MIB capabilities"

    SUPPORTS           CISCO-ENTITY-FRU-CONTROL-MIB
        INCLUDES           {
                           cefcMIBPowerModeGroup,
                           cefcMIBPowerFRUControlGroup,
                           cefcMIBInLinePowerControlGroup,
                           cefcModuleTable,
                           cefcMgmtNotificationsGroup,
                           cefcMIBInLinePowerControlGroupRev1
                           }

        VARIATION      cefcPowerRedundancyMode
        ACCESS         read-only
        DESCRIPTION    "write access is not supported"

        VARIATION      cefcPowerUnits
        ACCESS         not-implemented
        DESCRIPTION    "Information not available"

        VARIATION      cefcTotalDrawnCurrent
        ACCESS         not-implemented
        DESCRIPTION    "Information not available"

        VARIATION      cefcTotalAvailableCurrent
        ACCESS         not-implemented
        DESCRIPTION    "Information not available"

        VARIATION      cefcPowerRedundancyOperMode
        ACCESS         not-implemented
        DESCRIPTION    "Information not available"

        VARIATION      cefcFRUPowerAdminStatus
        SYNTAX         INTEGER { on (1) }
        ACCESS         read-only
        DESCRIPTION    "Supports only enumeration 'on'"

        VARIATION      cefcFRUPowerOperStatus
        SYNTAX         INTEGER { on (2) }
        DESCRIPTION    "Supports only enumeration 'on'"

        VARIATION      cefcFRUCurrent
        ACCESS         not-implemented
        DESCRIPTION    "Information not available"

        VARIATION      cefcMaxDefaultInLinePower
        ACCESS         not-implemented
        DESCRIPTION    "Information not available"

        VARIATION      cefcFRUTotalSystemCurrent
        ACCESS         not-implemented
        DESCRIPTION    "Information not available"

        VARIATION      cefcFRUDrawnSystemCurrent
        ACCESS         not-implemented
        DESCRIPTION    "Information not available"

        VARIATION      cefcFRUTotalInlineCurrent
        ACCESS         not-implemented
        DESCRIPTION    "Information not available"

        VARIATION      cefcFRUDrawnInlineCurrent
        ACCESS         not-implemented
        DESCRIPTION    "Information not available"

        VARIATION      cefcModuleAdminStatus
        ACCESS         read-only
        DESCRIPTION    "Write access is not supported"

        VARIATION      cefcModuleLastClearConfigTime
        ACCESS         not-implemented
        DESCRIPTION    "Information not available"

        VARIATION      cefcModuleResetReasonDescription
        ACCESS         not-implemented
        DESCRIPTION    "Information not available"

        VARIATION      cefcModuleStateChangeReasonDescr
        ACCESS         not-implemented
        DESCRIPTION    "Information not available"

        VARIATION      cefcModuleUpTime
        ACCESS         not-implemented
        DESCRIPTION    "Information not available"

        VARIATION      cefcPowerStatusChange
        ACCESS         not-implemented
        DESCRIPTION    "Information not available"

        VARIATION      cefcMaxDefaultHighInLinePower
        ACCESS         not-implemented
        DESCRIPTION    "Information not available"

    ::= { ciscoEntityFruControlCapability 17 }

ciscoEfcCapCatOSV08R0501 AGENT-CAPABILITIES
    PRODUCT-RELEASE     "Cisco CatOS 8.5(1) on Catalyst 6000/6500
                         and Cisco 7600 series devices."
    STATUS              current
    DESCRIPTION         "CISCO-ENTITY-FRU-CONTROL-MIB capabilities."

    SUPPORTS            CISCO-ENTITY-FRU-CONTROL-MIB
        INCLUDES        { cefcMIBPowerModeGroup,
                          cefcMIBPowerFRUControlGroup,
                          cefcMIBModuleGroup,
                          cefcMIBInLinePowerControlGroup,
                          cefcMIBNotificationEnablesGroup,
                          cefcMIBNotificationEnablesGroup2,
                          cefcMgmtNotificationsGroup,
                          cefcMgmtNotificationsGroup3,
                          cefcIntelliModuleGroup,
                          cefcPowerCapacityGroup,
                          cefcCoolingGroup,
                          cefcConnectorRatingGroup,
                          cefcMIBInLinePowerControlGroupRev1 }

        VARIATION              cefcFRUPowerAdminStatus
        SYNTAX                 INTEGER { on(1),
                                         off(2),
                                         inlineAuto(3),
                                         reset(5) }
        DESCRIPTION            "Only limited set of enumerated values
                                are supported."

        VARIATION              cefcModuleAdminStatus
        SYNTAX                 INTEGER { enabled(1),
                                         disabled(2),
                                         reset(3) }
        DESCRIPTION            "Only limited set of enumerated values
                                are supported."

        VARIATION        cefcModuleStatusChange -- NOTIFICATION-TYPE
--          OBJECTS       { cefcModuleOperStatus,
--                          cefcModuleStatusLastChangeTime,
--                          entPhysicalDescr,
--                          entPhysicalName 
--                        }
            DESCRIPTION
                    "In addition to the regular varbinds, the instance 
                     values of entPhysicalDescr and entPhysicalName are 
                     appended to the notification."

        VARIATION        cefcPowerStatusChange -- NOTIFICATION-TYPE
--          OBJECTS       { cefcFRUPowerOperStatus,
--                          cefcFRUPowerAdminStatus,
--                          entPhysicalDescr,
--                          entPhysicalName 
--                        }
            DESCRIPTION
                    "In addition to the regular varbinds, the instance 
                     values of entPhysicalDescr and entPhysicalName are 
                     appended to the notification."

        VARIATION        cefcFRUInserted -- NOTIFICATION-TYPE
--          OBJECTS       { entPhysicalContainedIn,
--                          entPhysicalDescr,
--                          entPhysicalName
--                        }
            DESCRIPTION
                    "In addition to the regular varbinds, the instance 
                     values of entPhysicalDescr and entPhysicalName are 
                     appended to the notification."

        VARIATION        cefcFRURemoved -- NOTIFICATION-TYPE
--          OBJECTS       { entPhysicalContainedIn,
--                          entPhysicalDescr,
--                          entPhysicalName
--                        }
            DESCRIPTION
                    "In addition to the regular varbinds, the instance 
                     values of entPhysicalDescr and entPhysicalName are 
                     appended to the notification."

    ::= { ciscoEntityFruControlCapability 18 }

ciscoEfcCapSanOSV21R1MDS9000 AGENT-CAPABILITIES
    PRODUCT-RELEASE     "Cisco SanOS 2.1(1) on Cisco MDS 9000 series
                         devices."
    STATUS              current
    DESCRIPTION         "CISCO-ENTITY-FRU-CONTROL-MIB capabilities."

    SUPPORTS            CISCO-ENTITY-FRU-CONTROL-MIB
        INCLUDES        { cefcMIBPowerModeGroup,
                          cefcMIBPowerFRUControlGroup,
                          cefcMIBInLinePowerControlGroup,
                          cefcMIBPowerFRUValueGroup,
                          cefcMIBModuleGroup,
                          cefcModuleGroupRev1,
                          cefcMIBNotificationEnablesGroup,
                          cefcMgmtNotificationsGroup,
                          cefcMIBFanTrayStatusGroup,
                          cefcMIBPhysicalGroup }

        VARIATION       cefcFRUInserted  -- NOTIFICATION-TYPE
--      OBJECTS         { entPhysicalContainedIn,
--                        entPhysicalDescr }
        DESCRIPTION     "The cefcFRUInserted notification indicates
                         that a FRU was inserted. The varbinds for
                         this notification indicate the
                         entPhysicalDescr of the inserted FRU and the
                         entPhysicalIndex of the FRU's container."

        VARIATION       cefcFRURemoved  -- NOTIFICATION-TYPE
--      OBJECTS         { entPhysicalContainedIn,
--                        entPhysicalDescr }
        DESCRIPTION     "The cefcFRURemoved notification indicates 
                         that a FRU was removed. The varbinds for this
                         notification indicate the entPhysicalDescr of
                         the removed FRU and the entPhysicalIndex of
                         the FRU's container."
 ::= { ciscoEntityFruControlCapability 19 }

ciscoEfcCapSanOSV30R1MDS9000 AGENT-CAPABILITIES
    PRODUCT-RELEASE     "Cisco SanOS 3.0(1) on Cisco MDS 9000 series
                         devices."
    STATUS              current
    DESCRIPTION         "CISCO-ENTITY-FRU-CONTROL-MIB capabilities."

    SUPPORTS            CISCO-ENTITY-FRU-CONTROL-MIB
        INCLUDES        { cefcMIBPowerModeGroup,
                          cefcMIBPowerFRUControlGroup,
                          cefcMIBInLinePowerControlGroup,
                          cefcMIBPowerFRUValueGroup,
                          cefcMIBModuleGroup,
                          cefcModuleGroupRev1,
                          cefcMIBNotificationEnablesGroup,
                          cefcMgmtNotificationsGroup,
                          cefcMIBFanTrayStatusGroup,
                          cefcMIBPhysicalGroup,
                          cefcMgmtNotificationsGroup2 }

        VARIATION       cefcFRUInserted  -- NOTIFICATION-TYPE
--      OBJECTS         { entPhysicalContainedIn,
--                        entPhysicalDescr,
--                        entPhysicalName }
        DESCRIPTION     "The cefcFRUInserted notification indicates
                         that a FRU was inserted. The varbind for
                         this notification indicates the
                         entPhysicalIndex of the FRU's container,
                         entPhysicalDescr of the inserted FRU and 
                         the entPhysicalName of the inserted FRU's 
                         container."
        VARIATION       cefcFRURemoved  -- NOTIFICATION-TYPE
--      OBJECTS         { entPhysicalContainedIn,
--                        entPhysicalDescr,
--                        entPhysicalName }
        DESCRIPTION     "The cefcFRURemoved notification indicates 
                         that a FRU was removed. The varbind for this
                         notification indicates the entPhysicalIndex 
                         of the removed FRU's container, the
                         entPhysicalDescr of the removed FRU and 
                         the entPhysicalName of the removed FRU's 
                         container."
    ::= { ciscoEntityFruControlCapability 20 }

ciscoEfcCapACSWV03R000 AGENT-CAPABILITIES
    PRODUCT-RELEASE     "ACSW (Application Control Software) 3.0"
    STATUS              current
    DESCRIPTION         "CISCO-ENTITY-FRU-CONTROL-MIB capabilities."

    SUPPORTS            CISCO-ENTITY-FRU-CONTROL-MIB
        INCLUDES        { cefcMIBModuleGroup, cefcModuleGroupRev1,
                          cefcModuleExtGroup }

        VARIATION      cefcModuleAdminStatus
        ACCESS         read-only
        DESCRIPTION    "Create operation not supported."

    ::= { ciscoEntityFruControlCapability 21 }

END
