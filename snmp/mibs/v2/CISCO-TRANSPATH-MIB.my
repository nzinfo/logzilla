-- ****************************************************
-- CISCO-TRANSPATH-MIB:    TransPath Specific MIB
--
-- August 17, 1998. CISCO TISU EMS Group.
--
-- Copyright (c) 1998 by Cisco Systems, Inc.
-- All rights reserved.   
--
-- ****************************************************

CISCO-TRANSPATH-MIB DEFINITIONS ::= BEGIN

   IMPORTS
       MODULE-IDENTITY, OBJECT-TYPE, 
       NOTIFICATION-TYPE                FROM SNMPv2-SMI
       ciscoExperiment                  FROM CISCO-SMI
       DisplayString                    FROM SNMPv2-TC
       enterprises                      FROM SNMPv2-SMI
       Counter32                        FROM SNMPv2-SMI;

--
-- transpath          OBJECT IDENTIFIER ::= {ciscoExperiment 999}
--
   lightspeed         OBJECT IDENTIFIER ::= {enterprises 2496}
   lightspeedProducts OBJECT IDENTIFIER ::= {lightspeed 1}
   transpath          OBJECT IDENTIFIER ::= {lightspeedProducts 1}
   
-- ~~~~~~~~~~~~~~~~~~~~~~~
-- TransPath Main Branches
-- ~~~~~~~~~~~~~~~~~~~~~~~
tpOperational        OBJECT IDENTIFIER ::= { transpath 1 }
tpProvisioning       OBJECT IDENTIFIER ::= { transpath 2 }
tpMeasurement        OBJECT IDENTIFIER ::= { transpath 3 }
tpTrapsPrefix        OBJECT IDENTIFIER ::= { transpath 4 }
tpTraps              OBJECT IDENTIFIER ::= { tpTrapsPrefix 0 }
tpRecords            OBJECT IDENTIFIER ::= { transpath 5 }

-- ~~~~~~~~~~~~~~~~
-- OPERATIONAL CORE MIB Objects 
-- ~~~~~~~~~~~~~~~~ 
ciscoTPOperationalMIB MODULE-IDENTITY LAST-UPDATED "9808180000Z"
      ORGANIZATION "Cisco Systems, Inc."
      CONTACT-INFO
		 "Telephony Internet Services Unit
                  Cisco Systems, Inc.
                  Postal: 13615 Dulles Technology Drive
                  Herndon, Virginia 20171
                  USA
                  Tel: +1 (703) 484-3000"
      DESCRIPTION
         "Cisco TransPath MIB."
      REVISION    "9903010000Z"
      DESCRIPTION
         "Initial version of this MIB module."
      REVISION    "9808180000Z"
      DESCRIPTION
         "1. Revised to use the experimental branch of Cisco mib 
	     tree. 
	  2. Update the component table 
	     - Remove the tpComponentIndex.
	     - Provide better descriptions of the tpComponentId.
	  3. Re-design the operational mib."
      REVISION    "9909130000Z"
      DESCRIPTION
         "Change transpath oid from 21 to 999."
      REVISION    "9912170000Z"
      DESCRIPTION
         "Change MML name length to 20."
      REVISION    "2K03240000Z"
      DESCRIPTION
         "change the enterprise oid from Cisco's to LightSpeed's 2496" 
      ::= {tpOperational 1}


-- ~~~~~~~~~~~~~~~~~~~~~~~~~~~~~~~
-- TransPath Operational Component
-- ~~~~~~~~~~~~~~~~~~~~~~~~~~~~~~~
ciscoTPOperationalMIBObjects OBJECT IDENTIFIER ::= { ciscoTPOperationalMIB 1 }
tpCompGroup OBJECT IDENTIFIER ::= { ciscoTPOperationalMIBObjects 1 }
tpAlarmGroup OBJECT IDENTIFIER ::= { ciscoTPOperationalMIBObjects 2 }

tpCompTable OBJECT-TYPE
   SYNTAX SEQUENCE OF TpCompTableEntry
   MAX-ACCESS not-accessible
   STATUS current
   DESCRIPTION
       "TransPath operational components table."
   ::= {tpCompGroup 1}

tpCompTableEntry OBJECT-TYPE
   SYNTAX TpCompTableEntry
   MAX-ACCESS not-accessible
   STATUS current
   DESCRIPTION
       "TransPath component entry definition."
   INDEX {tpComponentId}
   ::= {tpCompTable 1}

TpCompTableEntry ::=
    SEQUENCE 
    {
        tpComponentId	INTEGER,
        tpComponentType	INTEGER,
        tpCompParentId	INTEGER,
        tpCompMMLName	DisplayString,
        tpCompDesc	DisplayString,
     	tpCompOpStatus 	DisplayString	
    }

tpComponentId OBJECT-TYPE
    SYNTAX INTEGER (1.. 4294967295)
    MAX-ACCESS  not-accessible
    STATUS  current
    DESCRIPTION
        "The component identification number. This number consists of
	 two parts, the component type and component instance. The
	 most significant 2-bytes signifies the component type, and the 
	 lower 2 bytes is the sequential instance of the type."
    ::= {tpCompTableEntry 1}

tpComponentType OBJECT-TYPE
    SYNTAX INTEGER (1.. 4294967295)
    MAX-ACCESS  read-only
    STATUS  current
    DESCRIPTION
        "The component type identification number.i"
    ::= {tpCompTableEntry 2}

tpCompParentId OBJECT-TYPE
    SYNTAX INTEGER  (1.. 4294967295)
    MAX-ACCESS read-only
    STATUS  current
    DESCRIPTION
         "The component parent identification."
    ::= {tpCompTableEntry 3}

tpCompMMLName OBJECT-TYPE
    SYNTAX DisplayString (SIZE (1.. 20))
    MAX-ACCESS read-only
    STATUS  current
    DESCRIPTION
        "This is a short notation of the component name. It is also the
	 MML (man-machine language) name that can be used in the MML
	 session."
    ::= {tpCompTableEntry 4}

tpCompDesc OBJECT-TYPE
    SYNTAX DisplayString (SIZE (0.. 128))
    MAX-ACCESS read-only
    STATUS  current
    DESCRIPTION
         "The component description"
    ::= {tpCompTableEntry 5}

tpCompOpStatus OBJECT-TYPE
    SYNTAX DisplayString (SIZE (0.. 15))
    MAX-ACCESS read-only
    STATUS current
    DESCRIPTION
        "The operational status of the component"
    ::= {tpCompTableEntry 6}


-- ~~~~~~~~~~~~~~~~~~~~
-- Alarm Record Objects
-- ~~~~~~~~~~~~~~~~~~~~
tpAlarmObject OBJECT IDENTIFIER ::= { tpRecords 5 }

tpAlarmId OBJECT-TYPE
    SYNTAX  INTEGER (1.. 4294967295)
    MAX-ACCESS not-accessible
    STATUS  current
    DESCRIPTION
        "The alarm indentification"
    ::= {tpAlarmObject 1}

tpAlarmCatId OBJECT-TYPE
    SYNTAX  INTEGER (1.. 90000)
    MAX-ACCESS  not-accessible
    STATUS  current
    DESCRIPTION
        "The alarm category identification number"
    ::= {tpAlarmObject 2}

tpAlarmCatName OBJECT-TYPE
    SYNTAX DisplayString (SIZE (0.. 15))
    MAX-ACCESS  not-accessible
    STATUS  current
    DESCRIPTION
         "The alarm category name"
    ::= {tpAlarmObject 3}

tpAlarmCatDesc OBJECT-TYPE
    SYNTAX DisplayString (SIZE (0.. 128))
    MAX-ACCESS not-accessible
    STATUS  current
    DESCRIPTION
        "The alarm category description"
    ::= {tpAlarmObject 4}

tpAlarmSet OBJECT-TYPE
    SYNTAX INTEGER 
    {
        clear (1),
        set (2)
    }
    MAX-ACCESS not-accessible
    STATUS  current
    DESCRIPTION
        "The alarm set or not."
    ::= {tpAlarmObject 5}

tpAlarmNotify OBJECT-TYPE
    SYNTAX INTEGER 
    {
         no (1),
         yes (2)
    }
    MAX-ACCESS read-only
    STATUS  current
    DESCRIPTION
         "The alarm has been notified or not."
    ::= {tpAlarmObject 6}

tpAlarmSeverity OBJECT-TYPE
    SYNTAX INTEGER 
    {
         informational (1),
         minor (2),
         major (3),
         critical (4)
    }
    MAX-ACCESS not-accessible
    STATUS  current
    DESCRIPTION
         "The alarm severity."
    ::= {tpAlarmObject 7}

tpAlarmReported OBJECT-TYPE
    SYNTAX INTEGER 
    {
         no (1),
         yes (2)
    }
    MAX-ACCESS not-accessible
    STATUS  current
    DESCRIPTION
         "The alarm reported."
    ::= {tpAlarmObject 8}

tpAlarmTime OBJECT-TYPE
    SYNTAX Counter32 
    MAX-ACCESS not-accessible
    STATUS  current
    DESCRIPTION
         "The time when alarm occured."
    ::= {tpAlarmObject 9}


-- ~~~~~~~~~~~~~~~~~~~~~~~~~~~~~~~~~~~
-- Transpath Enterprise Specific Traps
-- ~~~~~~~~~~~~~~~~~~~~~~~~~~~~~~~~~~~

commAlarm NOTIFICATION-TYPE
    OBJECTS 
    {
	 tpAlarmId,
         tpAlarmCatId, 
         tpAlarmCatName, 
         tpAlarmCatDesc, 
         tpAlarmSet, 
         tpAlarmNotify, 
         tpAlarmSeverity, 
         tpAlarmReported, 
	 tpComponentId,
	 tpComponentType,
	 tpCompMMLName,
	 tpCompDesc,
	 tpCompParentId,
	 tpAlarmTime
    }
    STATUS current
    DESCRIPTION
         "Notification of a communication error.  This shows 
          which component had failed, the fault type and severity 
          level and the time it occurred from the MIB-II restart time. 
          Because many of the failures need to be described in detail 
          for troubleshooting, an alarm log is written with supplemental 
          information.  The trap and log are correlated based on the 
          alarm time."
    ::= {tpTraps 1}

qualityOfService NOTIFICATION-TYPE
    OBJECTS 
    { 
	 tpAlarmId,
         tpAlarmCatId, 
         tpAlarmCatName, 
         tpAlarmCatDesc, 
         tpAlarmSet, 
         tpAlarmNotify, 
         tpAlarmSeverity, 
         tpAlarmReported, 
	 tpComponentId,
	 tpComponentType,
	 tpCompMMLName,
	 tpCompDesc,
	 tpCompParentId,
         tpAlarmTime
    }
    STATUS current
    DESCRIPTION
         "Notification when there is a failure in the quality of service. 
          This shows which component had failed, its operational status, 
          fault type and severity level and the time it occurred from the 
          MIB-II restart time. Because many of the failures need to be 
          described in detail for troubleshooting, an alarm log is written 
          with supplemental information.  The trap and log are correlated 
          based on the alarm time."
    ::= {tpTraps 2}

processingError NOTIFICATION-TYPE
    OBJECTS 
    { 
	 tpAlarmId,
         tpAlarmCatId, 
         tpAlarmCatName, 
         tpAlarmCatDesc, 
         tpAlarmSet, 
         tpAlarmNotify, 
         tpAlarmSeverity, 
         tpAlarmReported, 
	 tpComponentId,
	 tpComponentType,
	 tpCompMMLName,
	 tpCompDesc,
	 tpCompParentId,
         tpAlarmTime
    }
    STATUS current
    DESCRIPTION
         "Notification of a process fault. This shows which component had 
          failed, its operational status, fault type and severity level and 
          the time it occurred from the MIB-II restart time. Because many 
          of the failures need to be described in detail for troubleshooting, 
          an alarm log is written with supplemental information.  The trap 
          and log are correlated based on the alarm time."
    ::= {tpTraps 3}

equipmentError NOTIFICATION-TYPE
    OBJECTS 
    { 
	 tpAlarmId,
         tpAlarmCatId, 
         tpAlarmCatName, 
         tpAlarmCatDesc, 
         tpAlarmSet, 
         tpAlarmNotify, 
         tpAlarmSeverity, 
         tpAlarmReported, 
	 tpComponentId,
	 tpComponentType,
	 tpCompMMLName,
	 tpCompDesc,
	 tpCompParentId,
         tpAlarmTime
    }
    STATUS current
    DESCRIPTION
         "Notification of an equipment error in the TransPath system. 
          This shows which component had failed, its operational status, 
          fault type and severity level and the time it occurred from the 
          MIB-II restart time. Because many of the failures need to be 
          described in detail for troubleshooting, an alarm log is written 
          with supplemental information.  The trap and log are correlated 
          based on the alarm time."
    ::= {tpTraps 4}

environmentError NOTIFICATION-TYPE
    OBJECTS 
    { 
	 tpAlarmId,
         tpAlarmCatId, 
         tpAlarmCatName, 
         tpAlarmCatDesc, 
         tpAlarmSet, 
         tpAlarmNotify, 
         tpAlarmSeverity, 
         tpAlarmReported, 
	 tpComponentId,
	 tpComponentType,
	 tpCompMMLName,
	 tpCompDesc,
	 tpCompParentId,
         tpAlarmTime
    }
    STATUS current
    DESCRIPTION
         "Notification of an TransPath system.s environment problem. 
          This shows which component had failed, its operational status, 
          fault type and severity level and the time it occurred from the 
          MIB-II restart time. Because many of the failures need to be 
          described in detail for troubleshooting, an alarm log is written 
          with supplemental information.  The trap and log are correlated 
          based on the alarm time."
    ::= {tpTraps 5}

END
