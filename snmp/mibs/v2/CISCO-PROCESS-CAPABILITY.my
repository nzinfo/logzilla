-- *****************************************************************
-- CISCO-PROCESS-CAPABILITY.my: CISCO-PROCESS-MIB AGENT-CAPABILITIES
--
-- November 2001, Srinivas Davuluri
-- August   2003, Padma Pullela
-- November 2004, Nandini. V
--
-- Copyright (c) 2001, 2003, 2004, 2005 by cisco Systems, Inc.
-- All rights reserved.
--
-- *****************************************************************

CISCO-PROCESS-CAPABILITY DEFINITIONS ::= BEGIN

IMPORTS
        MODULE-IDENTITY
                FROM SNMPv2-SMI
        AGENT-CAPABILITIES
                FROM SNMPv2-CONF
        ciscoAgentCapability
                FROM CISCO-SMI;   

ciscoProcessCapability MODULE-IDENTITY
                LAST-UPDATED    "200602210000Z"
                ORGANIZATION    "Cisco Systems, Inc."
                CONTACT-INFO  
                        "       Cisco Systems
                                Customer Service

                        Postal: 170 West Tasman Drive
                                San Jose, CA  95134
                                USA

                           Tel: +1 800 553-NETS

                        E-mail: cs-snmp@cisco.com
                                cs-lan-switch-snmp@cisco.com"
                DESCRIPTION
                        "Agent capabilities for CISCO-PROCESS-MIB"

               REVISION        "200602210000Z"
                    DESCRIPTION
                        "-Added Agent capabilities 
                          ciscoProcessCapabilityACSWV03R000 for 
                          Cisco Application Control Engine (ACE)."

               REVISION        "200512120000Z"
                    DESCRIPTION
                        "-Added ciscoProcessCapabilitySANOSV3R0001 for
                          SAN-OS 3.0(1)."

               REVISION        "200411050000Z"
            DESCRIPTION
                        "-Added ciscoProcessCapabilityV12R02S for 
                          Cisco IOS 12.2(S).
                         -Added ciscoProcessCapabilityV12R03 for
                          Cisco IOS 12.3.
                         -Added ciscoProcessCapabilityV12R03T for
                          Cisco IOS 12.3(T)"
              
                REVISION        "200308060000Z"
                DESCRIPTION
                        "Added ciscoProcessCapCatOSV07R0201 for
                         Cisco CatOS 7.2(1)." 

                REVISION        "200111200000Z"
                DESCRIPTION
                        "Initial version of this MIB module."
        ::= { ciscoAgentCapability 256 }

ciscoProcessCapabilityV12R00 AGENT-CAPABILITIES

PRODUCT-RELEASE    "Cisco IOS 12.0S"
STATUS        current
DESCRIPTION    "IOS 12.0S CISCO-PROCESS-MIB capabilities"

SUPPORTS    CISCO-PROCESS-MIB
INCLUDES    {    cpmCPUTotalGroup, cpmProcessGroup,
            cpmProcessExtGroup, cpmCPUTotalGroupRev,
            cpmProcessExtGroupRev, cpmProcessGroupRev
        }    

VARIATION    cpmProcExtPriority
ACCESS          read-only
DESCRIPTION    "Write access is not required."

::= { ciscoProcessCapability 1 }


ciscoProcessCapabilityV12R01 AGENT-CAPABILITIES

PRODUCT-RELEASE    "Cisco IOS 12.1"
STATUS        current
DESCRIPTION    "IOS 12.1 CISCO-PROCESS-MIB capabilities"

SUPPORTS    CISCO-PROCESS-MIB
INCLUDES    {    cpmCPUTotalGroup, cpmProcessGroup,
            cpmProcessExtGroup, cpmCPUTotalGroupRev,
            cpmProcessExtGroupRev, cpmProcessGroupRev
        }    

VARIATION    cpmProcExtPriority
ACCESS          read-only
DESCRIPTION    "Write access is not required."

::= { ciscoProcessCapability 2 }


ciscoProcessCapabilityV12R02 AGENT-CAPABILITIES

PRODUCT-RELEASE    "Cisco IOS 12.2"
STATUS        current
DESCRIPTION    "IOS 12.2 CISCO-PROCESS-MIB capabilities"

SUPPORTS    CISCO-PROCESS-MIB
INCLUDES    {    cpmCPUTotalGroup, cpmProcessGroup,
            cpmProcessExtGroup, cpmCPUTotalGroupRev,
            cpmProcessExtGroupRev, cpmProcessGroupRev
        }    

VARIATION    cpmProcExtPriority
ACCESS          read-only
DESCRIPTION    "Write access is not required."

::= { ciscoProcessCapability 3 }


ciscoProcessCapCatOSV07R0201 AGENT-CAPABILITIES

PRODUCT-RELEASE    "Cisco CatOS 7.2(1)"
STATUS        current
DESCRIPTION    "CISCO-PROCESS-MIB capabilities"

SUPPORTS    CISCO-PROCESS-MIB
INCLUDES    { cpmCPUTotalGroup, cpmProcessGroup,
                  cpmProcessExtGroup, cpmProcessExtGroupRev, 
          cpmCPUTotalGroupRev, cpmProcessGroupRev
        }    

VARIATION       cpmProcExtPriority
ACCESS          read-only
DESCRIPTION     "Write access is not required."

::= { ciscoProcessCapability 4 }


ciscoProcessCapabilityV12R02S AGENT-CAPABILITIES

PRODUCT-RELEASE    "Cisco IOS 12.2S"
STATUS        current
DESCRIPTION    "IOS 12.2 CISCO-PROCESS-MIB capabilities"

SUPPORTS    CISCO-PROCESS-MIB
INCLUDES    {    cpmCPUTotalGroup, cpmProcessGroup,
            cpmProcessExtGroup, cpmCPUTotalGroupRev,
            cpmProcessExtGroupRev, cpmProcessGroupRev,
            cpmCPUHistoryGroup, cpmCPUThresholdGroup
        }    

VARIATION    cpmProcExtPriority
ACCESS          read-only
DESCRIPTION    "Write access is not required."

VARIATION    cpmCPUHistorySize
ACCESS          read-only
DESCRIPTION    "Write not implemented."

VARIATION    cpmCPUHistoryThreshold
ACCESS          read-only
DESCRIPTION    "Write/create not implemented."

VARIATION    cpmCPUThresholdEntryStatus
ACCESS          read-only
DESCRIPTION    "Write/create not implemented."

VARIATION    cpmCPURisingThresholdValue
ACCESS          read-only
DESCRIPTION    "Write/create not implemented."

VARIATION    cpmCPURisingThresholdPeriod
ACCESS          read-only
DESCRIPTION    "Write/create  not implemented."

VARIATION    cpmCPUFallingThresholdValue
ACCESS          read-only
DESCRIPTION    "Write/create  not implemented."

::= { ciscoProcessCapability 5 }


ciscoProcessCapabilityV12R03 AGENT-CAPABILITIES

PRODUCT-RELEASE    "Cisco IOS 12.3"
STATUS        current
DESCRIPTION    "IOS 12.3 CISCO-PROCESS-MIB capabilities"

SUPPORTS    CISCO-PROCESS-MIB
INCLUDES    {    cpmCPUTotalGroup, cpmProcessGroup,
            cpmProcessExtGroup, cpmCPUTotalGroupRev,
            cpmProcessExtGroupRev, cpmProcessGroupRev
        }    

VARIATION    cpmProcExtPriority
ACCESS          read-only
DESCRIPTION    "Write access is not required."

::= { ciscoProcessCapability 6 }


ciscoProcessCapabilityV12R03T AGENT-CAPABILITIES

PRODUCT-RELEASE    "Cisco IOS 12.3T"
STATUS        current
DESCRIPTION    "IOS 12.3T CISCO-PROCESS-MIB capabilities"

SUPPORTS    CISCO-PROCESS-MIB
INCLUDES    {    cpmCPUTotalGroup, cpmProcessGroup,
            cpmProcessExtGroup, cpmCPUTotalGroupRev,
            cpmProcessExtGroupRev, cpmProcessGroupRev,
            cpmCPUHistoryGroup, cpmCPUThresholdGroup
        }    

VARIATION    cpmProcExtPriority
ACCESS          read-only
DESCRIPTION    "Write access is not required."

VARIATION    cpmCPUHistorySize
ACCESS          read-only
DESCRIPTION    "Write not implemented."

VARIATION    cpmCPUHistoryThreshold
ACCESS          read-only
DESCRIPTION    "Write/create not implemented."

VARIATION    cpmCPUThresholdEntryStatus
ACCESS          read-only
DESCRIPTION    "Write/create not implemented."

VARIATION    cpmCPURisingThresholdValue
ACCESS          read-only
DESCRIPTION    "Write/create not implemented."

VARIATION    cpmCPURisingThresholdPeriod
ACCESS          read-only
DESCRIPTION    "Write/create  not implemented."

VARIATION    cpmCPUFallingThresholdValue
ACCESS          read-only
DESCRIPTION    "Write/create  not implemented."

::= { ciscoProcessCapability 7 }


ciscoProcessCapabilitySAN3R0001 AGENT-CAPABILITIES

PRODUCT-RELEASE "SAN-OS 3.0(1)"
STATUS          current
DESCRIPTION     "SAN-OS 3.0(1) CISCO-PROCESS-MIB capabilities"

SUPPORTS        CISCO-PROCESS-MIB
INCLUDES        {       
                        cpmProcessExtGroupRev, 
                        cpmProcessGroupRev
                }

::= { ciscoProcessCapability 8 }

ciscoProcessCapabilityACSWV03R000 AGENT-CAPABILITIES

PRODUCT-RELEASE "ACSW (Application Control Software) 3.0"
STATUS          current
DESCRIPTION     "ACSW 3.0 CISCO-PROCESS-MIB capabilities"

SUPPORTS        CISCO-PROCESS-MIB
INCLUDES        {
                        cpmProcessExtGroupRev, 
                        cpmProcessGroupRev,
                        cpmCPUTotalGroupRev1 
                }

VARIATION    cpmCPUInterruptMonIntervalValue
ACCESS          not-implemented
DESCRIPTION     "Not supported."


::= { ciscoProcessCapability 9 }

END
