-- *****************************************************************
-- CISCO-POWER-ETHERNET-EXT-CAPABILITY.my:
-- Cisco CISCO-POWER-ETHERNET-EXT-MIB AGENT-CAPABILITIES
--
-- June 2004, Seth Wang
--
-- Copyright (c) 2004, 2005 by Cisco Systems, Inc.
-- All rights reserved.
-- *****************************************************************

CISCO-POWER-ETHERNET-EXT-CAPABILITY DEFINITIONS ::= BEGIN

IMPORTS
        MODULE-IDENTITY, Unsigned32
                FROM SNMPv2-SMI
        AGENT-CAPABILITIES
                FROM SNMPv2-CONF
        ciscoAgentCapability
                FROM CISCO-SMI;

ciscoPowerEthernetExtCapability MODULE-IDENTITY
        LAST-UPDATED    "200406150000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-POWER-ETHERNET-EXT-MIB."

        REVISION        "200406150000Z"
        DESCRIPTION
                "Added capability statement
                 cPowerEthExtCapCatOSV08R0501."
        REVISION        "200406070000Z"
        DESCRIPTION
                "Initial version of this MIB module."
        ::= { ciscoAgentCapability 406 }

cPowerEthExtCapCatOSV08R0401 AGENT-CAPABILITIES
    PRODUCT-RELEASE     "Cisco CatOS 8.4(1)."
    STATUS              current
    DESCRIPTION         "CISCO-POWER-ETHERNET-EXT-MIB capabilities."

    SUPPORTS            CISCO-POWER-ETHERNET-EXT-MIB
        INCLUDES        { cpeExtPsePortGroup,
                          cpeExtPsePortGlobalConfigGroup }

        VARIATION       cpeExtPsePortPwrMax
            SYNTAX      Unsigned32 (4000..15400)
            DESCRIPTION "Only a limited set of values is supported."

        VARIATION       cpeExtDefaultAllocation
            SYNTAX      Unsigned32 (4000..15400)
            DESCRIPTION "Only a limited set of values is supported."

        VARIATION       cpeExtPsePortEnable
            SYNTAX      INTEGER { auto(1), static(2) }
            DESCRIPTION "The enumerated values supported are all those
                         defined at the time this clause was written."

    ::= { ciscoPowerEthernetExtCapability 1 }

cPowerEthExtCapCatOSV08R0501 AGENT-CAPABILITIES
    PRODUCT-RELEASE     "Cisco CatOS 8.5(1)."
    STATUS              current
    DESCRIPTION         "CISCO-POWER-ETHERNET-EXT-MIB capabilities."

    SUPPORTS            CISCO-POWER-ETHERNET-EXT-MIB
        INCLUDES        { cpeExtPsePortGroup,
                          cpeExtPsePortGlobalConfigGroup,
                          cpeExtPsePortPwrMonitorGroup,
                          cpeExtMainPseGroup }

        VARIATION       cpeExtPsePortPwrMax
            SYNTAX      Unsigned32 (4000..15400)
            DESCRIPTION "Only a limited set of values is supported."

        VARIATION       cpeExtDefaultAllocation
            SYNTAX      Unsigned32 (4000..15400)
            DESCRIPTION "Only a limited set of values is supported."

        VARIATION       cpeExtPsePortEnable
            SYNTAX      INTEGER { auto(1), static(2), limit(3) }
            DESCRIPTION "The enumerated values supported are all those
                         defined at the time this clause was written."

    ::= { ciscoPowerEthernetExtCapability 2 }

END
