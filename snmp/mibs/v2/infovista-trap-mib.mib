--------------------------------------------------------------------
-- InfoVista-trap-mib.mib: InfoVista Mib File (trap part)
--------------------------------------------------------------------

INFOVISTA-TRAP-MIB DEFINITIONS ::= BEGIN

IMPORTS
	OBJECT-TYPE
		 FROM RFC-1212
	TRAP-TYPE
		 FROM RFC-1215
	MODULE-IDENTITY,  Integer32, Counter32
		FROM SNMPv2-SMI
	InfoVista, InfoVistaOID
		FROM INFOVISTA-MIB;

	ivtrap MODULE-IDENTITY
		LAST-UPDATED	"9910271621Z"
		ORGANIZATION	"InfoVista S.A."
		CONTACT-INFO	"support@infovista.com"
		DESCRIPTION	"Extended trap definition."
		::= { InfoVista 6 }

	instance OBJECT-TYPE
	  SYNTAX  OCTET STRING
	  ACCESS  read-only
	  STATUS  mandatory
	  DESCRIPTION
			  "Name of the instance which caused the trap."
	  ::= { ivtrap 1 }

	indicator OBJECT-TYPE
	  SYNTAX  OCTET STRING
	  ACCESS  read-only
	  STATUS  mandatory
	  DESCRIPTION
			  "Name of the indicator which caused the trap."
	  ::= { ivtrap 2 }

	description OBJECT-TYPE
	  SYNTAX  OCTET STRING
	  ACCESS  read-only
	  STATUS  mandatory
	  DESCRIPTION
			  "Trap description."
	  ::= { ivtrap 3 }

	disprate OBJECT-TYPE
	  SYNTAX  Counter32
	  ACCESS  read-only
	  STATUS  mandatory
	  DESCRIPTION
			  "Display rate of the collector related to the indicator."
	  ::= { ivtrap 4 }

	instanceId OBJECT-TYPE
	  SYNTAX  Counter32
	  ACCESS  read-only
	  STATUS  mandatory
	  DESCRIPTION
			  "Identifier of the instance which caused the trap."
	  ::= { ivtrap 5 }

	indicatorId OBJECT-TYPE
	  SYNTAX  Counter32
	  ACCESS  read-only
	  STATUS  mandatory
	  DESCRIPTION
			  "Identifier of the indicator which caused the trap."
	  ::= { ivtrap 6 }

	description2 OBJECT-TYPE
	  SYNTAX  OCTET STRING
	  ACCESS  read-only
	  STATUS  mandatory
	  DESCRIPTION
			  "Secondary trap description."
	  ::= { ivtrap 7 }

	serial OBJECT-TYPE
	  SYNTAX  Counter32
	  ACCESS  read-only
	  STATUS  mandatory
	  DESCRIPTION
			  "Trap serial number."
	  ::= { ivtrap 8 }

	seconds OBJECT-TYPE
	  SYNTAX  Counter32
	  ACCESS  read-only
	  STATUS  mandatory
	  DESCRIPTION
			  "Trap timestamp in seconds (starting January 1st 1901)"
	  ::= { ivtrap 9 }

	endpoint OBJECT-TYPE
	  SYNTAX  Counter32
	  ACCESS  read-only
	  STATUS  mandatory
	  DESCRIPTION
			  "Collector endpoint as defined in the command line. This variable is null if the collector has been started without a specified endpoint."
	  ::= { ivtrap 10 }

	mEndpoint OBJECT-TYPE
	  SYNTAX  Counter32
	  ACCESS  read-only
	  STATUS  mandatory
	  DESCRIPTION
			  "Manager endpoint as defined in the setup. This variable is null if the manager endpoint is not defined."
	  ::= { ivtrap 11 }

	bEndpoint OBJECT-TYPE
	  SYNTAX  Counter32
	  ACCESS  read-only
	  STATUS  mandatory
	  DESCRIPTION
			  "Browser endpoint as defined in the setup. This variable is null if the browser endpoint is not defined."
	  ::= { ivtrap 12 }

	serverWid OBJECT-TYPE
	  SYNTAX  OCTET STRING
	  ACCESS  read-only
	  STATUS  mandatory
	  DESCRIPTION
			  "Server WID."
	  ::= { ivtrap 13 }

    IVTrapIndeterminate	TRAP-TYPE
      ENTERPRISE	InfoVistaOID
	  VARIABLES		{ instance, indicator, description, disprate, instanceId, indicatorId, description2, serial, seconds, endpoint, mEndpoint, bEndpoint, serverWid }
	  DESCRIPTION
			  "Indeterminate trap."
	  ::= 0

    IVTrapWarning	TRAP-TYPE
      ENTERPRISE	InfoVistaOID
	  VARIABLES		{ instance, indicator, description, disprate, instanceId, indicatorId, description2, serial, seconds, endpoint, mEndpoint, bEndpoint, serverWid }
	  DESCRIPTION
			  "Warning trap."
	  ::= 4

    IVTrapMinor	TRAP-TYPE
      ENTERPRISE	InfoVistaOID
	  VARIABLES		{ instance, indicator, description, disprate, instanceId, indicatorId, description2, serial, seconds, endpoint, mEndpoint, bEndpoint, serverWid }
	  DESCRIPTION
			  "Minor trap."
	  ::= 3

    IVTrapMajor	TRAP-TYPE
      ENTERPRISE	InfoVistaOID
	  VARIABLES		{ instance, indicator, description, disprate, instanceId, indicatorId, description2, serial, seconds, endpoint, mEndpoint, bEndpoint, serverWid }
	  DESCRIPTION
			  "Major trap."
	  ::= 2

    IVTrapCritical	TRAP-TYPE
      ENTERPRISE	InfoVistaOID
	  VARIABLES		{ instance, indicator, description, disprate, instanceId, indicatorId, description2, serial, seconds, endpoint, mEndpoint, bEndpoint, serverWid }
	  DESCRIPTION
			  "Critical trap."
	  ::= 1

    IVTrapCleared	TRAP-TYPE
      ENTERPRISE	InfoVistaOID
	  VARIABLES		{ instance, indicator, description, disprate, instanceId, indicatorId, description2, serial, seconds, endpoint, mEndpoint, bEndpoint, serverWid }
	  DESCRIPTION
			  "Cleared trap."
	  ::= 5
	  
END
