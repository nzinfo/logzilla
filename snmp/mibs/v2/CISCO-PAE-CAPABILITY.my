-- *****************************************************************
-- CISCO-PAE-CAPABILITY.my:
-- Cisco CISCO-PAE-MIB AGENT-CAPABILITIES
--
-- July 2003, Binh Le
--
-- Copyright (c) 2003-2004 by Cisco Systems, Inc.
-- All rights reserved.
-- *****************************************************************

CISCO-PAE-CAPABILITY DEFINITIONS ::= BEGIN

IMPORTS
        MODULE-IDENTITY,
        Unsigned32
                FROM SNMPv2-SMI
        AGENT-CAPABILITIES
                FROM SNMPv2-CONF
        ciscoAgentCapability
                FROM CISCO-SMI
        VlanIndex
                FROM CISCO-VTP-MIB;

ciscoPaeCapability MODULE-IDENTITY
        LAST-UPDATED    "200509050000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of CISCO-PAE-MIB."

        REVISION        "200509050000Z"
        DESCRIPTION
                "Added capability statement ciscoPaeCapCatOSV08R0501.

                 Added VARIATION for cpaeGuestVlanNumber in capability
                 statement ciscoPaeCapCatOSV08R0101Cat6K.

                 Added VARIATION for cpaeGuestVlanNumber in capability
                 statement ciscoPaeCapCatOSV08R0101Cat4K.

                 Added VARIATION for cpaeGuestVlanNumber in capability
                 statement ciscoPaeCapCatOSV08R0301"
        REVISION        "200401160000Z"
        DESCRIPTION
                "Added capability statement ciscoPaeCapCatOSV08R0301."

        REVISION        "200308060000Z"
        DESCRIPTION
                "Initial version of this MIB module."
        ::= { ciscoAgentCapability 319 }

ciscoPaeCapV12R0111bEXCat6K AGENT-CAPABILITIES
    PRODUCT-RELEASE     "Cisco IOS 12.1(11b)EX on Catalyst 6000/6500
                         and Cisco 7600 series devices."
    STATUS              current
    DESCRIPTION         "CISCO-PAE-MIB capabilities."

    SUPPORTS            CISCO-PAE-MIB
        INCLUDES        { cpaeMultipleHostGroup }
    ::= { ciscoPaeCapability 1 }

ciscoPaeCapCatOSV07R0101 AGENT-CAPABILITIES
    PRODUCT-RELEASE     "Cisco CatOS 7.1(1)."
    STATUS              current
    DESCRIPTION         "CISCO-PAE-MIB capabilities."

    SUPPORTS            CISCO-PAE-MIB
        INCLUDES        { cpaeMultipleHostGroup }
    ::= { ciscoPaeCapability 2 }

ciscoPaeCapCatOSV07R0501Cat6K AGENT-CAPABILITIES
    PRODUCT-RELEASE     "Cisco CatOS 7.5(1) on Catalyst 6000/6500
                         and Cisco 7600 series devices."
    STATUS              current
    DESCRIPTION         "CISCO-PAE-MIB capabilities."

    SUPPORTS            CISCO-PAE-MIB
        INCLUDES        { cpaeMultipleHostGroup, cpaePortEntryGroup,
                          cpaeGuestVlanGroup }
    ::= { ciscoPaeCapability 3 }

ciscoPaeCapCatOSV07R0601Cat6K AGENT-CAPABILITIES
    PRODUCT-RELEASE     "Cisco CatOS 7.6(1) on Catalyst 6000/6500
                         and Cisco 7600 series devices."
    STATUS              current
    DESCRIPTION         "CISCO-PAE-MIB capabilities."

    SUPPORTS            CISCO-PAE-MIB
        INCLUDES        { cpaeMultipleHostGroup, cpaePortEntryGroup,
                          cpaeGuestVlanGroup, cpaeShutdownTimeoutGroup }
    ::= { ciscoPaeCapability 4 }

ciscoPaeCapCatOSV08R0101Cat6K AGENT-CAPABILITIES
    PRODUCT-RELEASE     "Cisco CatOS 8.1(1) on Catalyst 6000/6500
                         and Cisco 7600 series devices."
    STATUS              current
    DESCRIPTION         "CISCO-PAE-MIB capabilities."

    SUPPORTS            CISCO-PAE-MIB
        INCLUDES        { cpaeMultipleHostGroup, cpaePortEntryGroup,
                          cpaeGuestVlanGroup, cpaeShutdownTimeoutGroup,
                          cpaeGuestVlanGroup2 }

        VARIATION       cpaeGuestVlanNumber
            SYNTAX      VlanIndex (0..4094)
            DESCRIPTION "Only limited set of values are supported."

    ::= { ciscoPaeCapability 5 }

ciscoPaeCapCatOSV08R0101Cat4K AGENT-CAPABILITIES
    PRODUCT-RELEASE     "Cisco CatOS 8.1(1) on Catalyst 4000 series
                         devices."
    STATUS              current
    DESCRIPTION         "CISCO-PAE-MIB capabilities."

    SUPPORTS            CISCO-PAE-MIB
        INCLUDES        { cpaeMultipleHostGroup, 
                          cpaeShutdownTimeoutGroup }

        VARIATION       cpaeGuestVlanNumber
            SYNTAX      VlanIndex (0..4094)
            DESCRIPTION "Only limited set of values are supported."

    ::= { ciscoPaeCapability 6 }

ciscoPaeCapCatOSV08R0301 AGENT-CAPABILITIES
    PRODUCT-RELEASE     "Cisco CatOS 8.3(1) on Catalyst 6000/6500
                         and Cisco 7600 series devices."
    STATUS              current
    DESCRIPTION         "CISCO-PAE-MIB capabilities."

    SUPPORTS            CISCO-PAE-MIB
        INCLUDES        { cpaeMultipleHostGroup, cpaePortEntryGroup,
                          cpaeGuestVlanGroup, cpaeShutdownTimeoutGroup,
                          cpaeGuestVlanGroup2, cpaeRadiusConfigGroup,
                          cpaeUserGroupGroup }

        VARIATION       cpaeGuestVlanNumber
            SYNTAX      VlanIndex (0..4094)
            DESCRIPTION "Only limited set of values are supported."

    ::= { ciscoPaeCapability 7 }

ciscoPaeCapCatOSV08R0501 AGENT-CAPABILITIES
    PRODUCT-RELEASE     "Cisco CatOS 8.5(1)."
    STATUS              current
    DESCRIPTION         "CISCO-PAE-MIB capabilities."
    SUPPORTS            CISCO-PAE-MIB
        INCLUDES        { cpaeMultipleHostGroup,
                          cpaePortEntryGroup,
                          cpaeGuestVlanGroup,
                          cpaeShutdownTimeoutGroup,
                          cpaeGuestVlanGroup2,
                          cpaeRadiusConfigGroup,
                          cpaeUserGroupGroup,
                          cpaeGuestVlanGroup3,
                          cpaePortAuthFailVlanGroup, 
                          cpaePortOperVlanGroup,
                          cpaeNoGuestVlanNotifEnableGrp,
                          cpaeNoAuthFailVlanNotifEnableGrp,
                          cpaeNoGuestVlanNotifGroup,
                          cpaeNoAuthFailVlanNotifGroup,
                          cpaeMacAuthBypassGroup,
                          cpaeWebAuthGroup,
                          cpaeAuthConfigGroup }

        VARIATION       cpaeGuestVlanNumber
            SYNTAX      VlanIndex (0..4094)
            DESCRIPTION "Only limited set of values are supported."

        VARIATION       cpaePortAuthFailVlan
            SYNTAX      VlanIndex (0..4094)
            DESCRIPTION "Only limited set of values are supported."

        VARIATION       cpaeMacAuthBypassReAuthTimeout
            SYNTAX      Unsigned32 (300..65535)
            DESCRIPTION "Only limited set of values are supported."

        VARIATION       cpaeMacAuthBypassShutdownTimeout
            SYNTAX      Unsigned32 (30..65535)
            DESCRIPTION "Only limited set of values are supported."

        VARIATION       cpaeMacAuthBypassAuthFailTimeout
            SYNTAX      Unsigned32 (5..65535)
            DESCRIPTION "Only limited set of values are supported."

        VARIATION       cpaeWebAuthSessionPeriod
            SYNTAX      Unsigned32 (300..86400)
            DESCRIPTION "Only limited set of values are supported."

        VARIATION       cpaeWebAuthQuietPeriod
            SYNTAX      Unsigned32 (1..43200)
            DESCRIPTION "Only limited set of values are supported."

        VARIATION       cpaeWebAuthMaxRetries
            SYNTAX      Unsigned32 (3..10)
            DESCRIPTION "Only limited set of values are supported."

        VARIATION       cpaeAuthReAuthPeriodSrcAdmin
            SYNTAX      INTEGER { auto(3) }
            DESCRIPTION "Only limited set of values are supported."

        VARIATION       cpaeAuthReAuthMax
            ACCESS      not-implemented
            DESCRIPTION "Not supported."

    ::= { ciscoPaeCapability 8 }

END
