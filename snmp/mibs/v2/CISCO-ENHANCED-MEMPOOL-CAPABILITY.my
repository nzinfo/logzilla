-- *****************************************************************
-- CISCO-ENHANCED-MEMPOOL-CAPABILITY.my: CISCO-ENHANCED-MEMPOOL-MIB 
--                                       AGENT-CAPABILITIES
-- 
-- October 2005, Sreenivasulu Chalamcharla
-- 
-- Copyright (c) 2004-2005 by Cisco Systems, Inc.
-- All rights reserved.
-- 
-- *****************************************************************

CISCO-ENHANCED-MEMPOOL-CAPABILITY DEFINITIONS ::= BEGIN

IMPORTS
        MODULE-IDENTITY
                FROM SNMPv2-SMI
        AGENT-CAPABILITIES
                FROM SNMPv2-CONF
        ciscoAgentCapability
            FROM CISCO-SMI;

cempCapability MODULE-IDENTITY
                LAST-UPDATED    "200510260000Z"
                ORGANIZATION    "Cisco Systems, Inc."
                CONTACT-INFO
                    "          Cisco Systems
                               Customer Service

                    Postal:    170 West Tasman Drive
                               San Jose, CA  95134
                               USA

                       Tel:    +1 800 553-NETS

                    E-mail:    cs-memory@cisco.com"
                DESCRIPTION
                        "Agent capabilities for
                         CISCO-ENHANCED-MEMPOOL-MIB"

		REVISION        "200510260000Z"
        	DESCRIPTION
               		 "Added cempCapabilityIOSXRV2R0CRS1 agent
			 capabilities for IOS XR release 2.0 CRS1"
                       
                REVISION        "200501270000Z"
                DESCRIPTION
                        "Added agent capabilities for 38xx, 37xx, 
                        26xx, 28xx, VG224 and IAD243x platforms."
                         
                REVISION        "200410010000Z"
                DESCRIPTION
                        "Added cempCapabilityV12R03TP5000 for 
                        Cisco IOS 12.3T"
                        
                REVISION        "200406150000Z"
                DESCRIPTION
                        "Initial version of this MIB module."
        ::= { ciscoAgentCapability 462 }

cempCapabilityV12R03T AGENT-CAPABILITIES

PRODUCT-RELEASE "Cisco IOS 12.3T"
STATUS          current
DESCRIPTION     "CISCO-ENHANCED-MEMPOOL MIB capabilities"

SUPPORTS        CISCO-ENHANCED-MEMPOOL-MIB
INCLUDES        { cempMemPoolGroup, cempMemPoolExtGroup,
                  cempMemBufferGroup, cempMemBufferExtGroup, 
                  cempMemBufferNotifyEnableGroup,
                  cempMemBufferNotifyGroup, cempMemPoolExtGroupRev1 }

VARIATION       cempMemBufferSize
ACCESS          read-only
DESCRIPTION     "Write access not implemented."

VARIATION       cempMemBufferMin
ACCESS          read-only
DESCRIPTION     "Write access not implemented."

VARIATION       cempMemBufferMax
ACCESS          read-only
DESCRIPTION     "Write access not implemented."

VARIATION       cempMemBufferPermanent
ACCESS          read-only
DESCRIPTION     "Write access not implemented."

VARIATION       cempMemBufferTransient
ACCESS          read-only
DESCRIPTION     "Write access not implemented."

VARIATION       cempMemBufferNotifyEnabled
ACCESS          read-only
DESCRIPTION     "Write access not implemented. Default
                 value is FALSE"

VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferFreeHit
ACCESS          not-implemented
DESCRIPTION     "This object is not supported in the current
                 MIB implementation."

VARIATION       cempMemBufferFreeMiss
ACCESS          not-implemented
DESCRIPTION     "This object is not supported in the current
                 MIB implementation."

        ::= { cempCapability 1 }
       
cempCapabilityV12R03TP5000 AGENT-CAPABILITIES

PRODUCT-RELEASE "Cisco IOS 12.3T for AS5350, AS5400 and AS5850
                platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 2 }

cempCapabilityV12R04TP37xx AGENT-CAPABILITIES

PRODUCT-RELEASE "Cisco IOS 12.4T for c3725 and c3745
                platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 3 }

cempCapabilityV12R04TP26xx AGENT-CAPABILITIES

PRODUCT-RELEASE "Cisco IOS 12.4T for c26xx and c2691
                platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 4 }

cempCapabilityV12R04TP38xx AGENT-CAPABILITIES

PRODUCT-RELEASE "Cisco IOS 12.4T for c3825 and c3845
                platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 5 }

cempCapabilityV12R04TP28xx AGENT-CAPABILITIES

PRODUCT-RELEASE "Cisco IOS 12.4T for c28xx platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 6 }

cempCapabilityV12R04TPVG224 AGENT-CAPABILITIES

PRODUCT-RELEASE "Cisco IOS 12.4T for VG224 platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 7 }

cempCapabilityV12R04TPIAD243x AGENT-CAPABILITIES

PRODUCT-RELEASE "Cisco IOS 12.4T for IAD243x platforms"
STATUS          current
DESCRIPTION     "CISCO-ENHANCED-MEMPOOL MIB capabilities"

SUPPORTS        CISCO-ENHANCED-MEMPOOL-MIB
INCLUDES        { cempMemPoolGroup, cempMemBufferNotifyEnableGroup,
                  cempMemPoolExtGroupRev1 }
                  
VARIATION       cempMemPoolUsedLowWaterMark
ACCESS          not-implemented
DESCRIPTION     "This object is not supported in the current
                 MIB implementation."

VARIATION       cempMemPoolAllocHit
ACCESS          not-implemented
DESCRIPTION     "This object is not supported in the current
                 MIB implementation."

VARIATION       cempMemPoolAllocMiss
ACCESS          not-implemented
DESCRIPTION     "This object is not supported in the current
                 MIB implementation."

VARIATION       cempMemPoolFreeHit
ACCESS          not-implemented
DESCRIPTION     "This object is not supported in the current
                 MIB implementation."

VARIATION       cempMemPoolFreeMiss
ACCESS          not-implemented
DESCRIPTION     "This object is not supported in the current
                 MIB implementation."

VARIATION       cempMemBufferNotifyEnabled
ACCESS          read-only
DESCRIPTION     "Write access not implemented."

        ::= { cempCapability 8 }

cempCapabilityIOSXRV2R0CRS1 AGENT-CAPABILITIES

PRODUCT-RELEASE  "Cisco IOS XR 2.0 for CRS-1"
STATUS           current
DESCRIPTION      "CISCO-ENHANCED-MEMPOOL-MIB capabilities for
		 IOS XR release 2.0"

SUPPORTS         CISCO-ENHANCED-MEMPOOL-MIB
INCLUDES         { cempMemPoolGroup }

   	::= { cempCapability 9 }

END
