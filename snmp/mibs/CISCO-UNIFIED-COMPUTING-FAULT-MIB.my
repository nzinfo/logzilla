-- *********************************************************************
-- CISCO-UNIFIED-COMPUTING-FAULT-MIB.my
-- 
-- MIB representation of the Cisco Unified Computing System
-- FAULT management information model package
-- 
-- Created December 2010 by Charles Bullis
-- 
-- Copyright (c) 2005-2010 Cisco Systems, Inc. All rights reserved.
-- 
-- *********************************************************************

CISCO-UNIFIED-COMPUTING-FAULT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    Counter32,
    CucsFaultCode,
    CucsFaultProbableCause,
    CucsFaultSeverity,
    CucsFaultType
        FROM CISCO-UNIFIED-COMPUTING-MIB
    CucsConditionLifecycle,
    CucsConditionRule,
    CucsConditionTag,
    CucsFaultPolicyClearAction
        FROM CISCO-UNIFIED-COMPUTING-TC-MIB;

cucsFaultObjects MODULE-IDENTITY
    LAST-UPDATED    "201004190000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        FAULT management information model package"
    ::= { ciscoUnifiedComputingMIBObjects 1 }

cucsFaultHolderTable OBJECT-TYPE
    SYNTAX           SEQUENCE OF CucsFaultHolderEntry
    MAX-ACCESS       not-accessible
    STATUS           current
    DESCRIPTION
        "Cisco UCS fault:Holder managed object table"
    ::= { cucsFaultObjects 2 }

cucsFaultHolderEntry OBJECT-TYPE
    SYNTAX           CucsFaultHolderEntry
    MAX-ACCESS       not-accessible
    STATUS           current
    DESCRIPTION
        "Entry for the cucsFaultHolderTable table."
    INDEX { cucsFaultHolderInstanceId }
    ::= { cucsFaultHolderTable 1 }

CucsFaultHolderEntry ::= SEQUENCE {
    cucsFaultHolderInstanceId                                        CucsManagedObjectId,
    cucsFaultHolderDn                                                CucsManagedObjectDn,
    cucsFaultHolderRn                                                SnmpAdminString,
    cucsFaultHolderName                                              SnmpAdminString,
    cucsFaultHolderTotalFaults                                       Unsigned64
}

cucsFaultHolderInstanceId OBJECT-TYPE
    SYNTAX       CucsManagedObjectId
    MAX-ACCESS   not-accessible
    STATUS       current
    DESCRIPTION
        "Instance identifier of the managed object."
    ::= { cucsFaultHolderEntry 1 }

cucsFaultHolderDn OBJECT-TYPE
    SYNTAX       CucsManagedObjectDn
    MAX-ACCESS   read-only
    STATUS       current
    DESCRIPTION
        "Cisco UCS fault:Holder:dn managed object property"
    ::= { cucsFaultHolderEntry 2 }

cucsFaultHolderRn OBJECT-TYPE
    SYNTAX       SnmpAdminString
    MAX-ACCESS   read-only
    STATUS       current
    DESCRIPTION
        "Cisco UCS fault:Holder:rn managed object property"
    ::= { cucsFaultHolderEntry 3 }

cucsFaultHolderName OBJECT-TYPE
    SYNTAX       SnmpAdminString
    MAX-ACCESS   read-only
    STATUS       current
    DESCRIPTION
        "Cisco UCS fault:Holder:name managed object property"
    ::= { cucsFaultHolderEntry 4 }

cucsFaultHolderTotalFaults OBJECT-TYPE
    SYNTAX       Unsigned64
    MAX-ACCESS   read-only
    STATUS       current
    DESCRIPTION
        "Cisco UCS fault:Holder:totalFaults managed object property"
    ::= { cucsFaultHolderEntry 5 }

cucsFaultTable OBJECT-TYPE
    SYNTAX           SEQUENCE OF CucsFaultEntry
    MAX-ACCESS       not-accessible
    STATUS           current
    DESCRIPTION
        "Cisco UCS fault:Inst managed object table"
    ::= { cucsFaultObjects 1 }

cucsFaultEntry OBJECT-TYPE
    SYNTAX           CucsFaultEntry
    MAX-ACCESS       not-accessible
    STATUS           current
    DESCRIPTION
        "Entry for the cucsFaultTable table."
    INDEX { cucsFaultIndex }
    ::= { cucsFaultTable 1 }

CucsFaultEntry ::= SEQUENCE {
    cucsFaultIndex                                                   CucsManagedObjectId,
    cucsFaultDn                                                      CucsManagedObjectDn,
    cucsFaultRn                                                      SnmpAdminString,
    cucsFaultAffectedObjectId                                        RowPointer,
    cucsFaultAffectedObjectDn                                        CucsManagedObjectDn,
    cucsFaultAck                                                     TruthValue,
    cucsFaultProbableCause                                           CucsFaultProbableCause,
    cucsFaultChangeSet                                               SnmpAdminString,
    cucsFaultCode                                                    CucsFaultCode,
    cucsFaultCreationTime                                            DateAndTime,
    cucsFaultDescription                                             SnmpAdminString,
    cucsFaultHighestSeverity                                         CucsFaultSeverity,
    cucsFaultId                                                      Unsigned64,
    cucsFaultLastModificationTime                                    DateAndTime,
    cucsFaultLc                                                      CucsConditionLifecycle,
    cucsFaultOccur                                                   Counter32,
    cucsFaultOrigSeverity                                            CucsFaultSeverity,
    cucsFaultPrevSeverity                                            CucsFaultSeverity,
    cucsFaultRule                                                    CucsConditionRule,
    cucsFaultSeverity                                                CucsFaultSeverity,
    cucsFaultTags                                                    CucsConditionTag,
    cucsFaultType                                                    CucsFaultType
}

cucsFaultIndex OBJECT-TYPE
    SYNTAX       CucsManagedObjectId
    MAX-ACCESS   not-accessible
    STATUS       current
    DESCRIPTION
        "Instance identifier of the managed object."
    ::= { cucsFaultEntry 1 }

cucsFaultDn OBJECT-TYPE
    SYNTAX       CucsManagedObjectDn
    MAX-ACCESS   read-only
    STATUS       current
    DESCRIPTION
        "Cisco UCS fault:Inst:dn managed object property"
    ::= { cucsFaultEntry 2 }

cucsFaultRn OBJECT-TYPE
    SYNTAX       SnmpAdminString
    MAX-ACCESS   read-only
    STATUS       current
    DESCRIPTION
        "Cisco UCS fault:Inst:rn managed object property"
    ::= { cucsFaultEntry 3 }

cucsFaultAffectedObjectId OBJECT-TYPE
    SYNTAX       RowPointer
    MAX-ACCESS   read-only
    STATUS       current
    DESCRIPTION
        "Cisco UCS fault:Inst:affectedObjectId managed object property"
    ::= { cucsFaultEntry 4 }

cucsFaultAffectedObjectDn OBJECT-TYPE
    SYNTAX       CucsManagedObjectDn
    MAX-ACCESS   read-only
    STATUS       current
    DESCRIPTION
        "Cisco UCS fault:Inst:affectedObjectDn managed object property"
    ::= { cucsFaultEntry 5 }

cucsFaultAck OBJECT-TYPE
    SYNTAX       TruthValue
    MAX-ACCESS   read-only
    STATUS       current
    DESCRIPTION
        "Cisco UCS fault:Inst:ack managed object property"
    ::= { cucsFaultEntry 6 }

cucsFaultProbableCause OBJECT-TYPE
    SYNTAX       CucsFaultProbableCause
    MAX-ACCESS   read-only
    STATUS       current
    DESCRIPTION
        "Cisco UCS fault:Inst:cause managed object property"
    ::= { cucsFaultEntry 7 }

cucsFaultChangeSet OBJECT-TYPE
    SYNTAX       SnmpAdminString
    MAX-ACCESS   read-only
    STATUS       current
    DESCRIPTION
        "Cisco UCS fault:Inst:changeSet managed object property"
    ::= { cucsFaultEntry 8 }

cucsFaultCode OBJECT-TYPE
    SYNTAX       CucsFaultCode
    MAX-ACCESS   read-only
    STATUS       current
    DESCRIPTION
        "Cisco UCS fault:Inst:code managed object property"
    ::= { cucsFaultEntry 9 }

cucsFaultCreationTime OBJECT-TYPE
    SYNTAX       DateAndTime
    MAX-ACCESS   read-only
    STATUS       current
    DESCRIPTION
        "Cisco UCS fault:Inst:created managed object property"
    ::= { cucsFaultEntry 10 }

cucsFaultDescription OBJECT-TYPE
    SYNTAX       SnmpAdminString
    MAX-ACCESS   read-only
    STATUS       current
    DESCRIPTION
        "Cisco UCS fault:Inst:descr managed object property"
    ::= { cucsFaultEntry 11 }

cucsFaultHighestSeverity OBJECT-TYPE
    SYNTAX       CucsFaultSeverity
    MAX-ACCESS   read-only
    STATUS       current
    DESCRIPTION
        "Cisco UCS fault:Inst:highestSeverity managed object property"
    ::= { cucsFaultEntry 12 }

cucsFaultId OBJECT-TYPE
    SYNTAX       Unsigned64
    MAX-ACCESS   read-only
    STATUS       current
    DESCRIPTION
        "Cisco UCS fault:Inst:id managed object property"
    ::= { cucsFaultEntry 13 }

cucsFaultLastModificationTime OBJECT-TYPE
    SYNTAX       DateAndTime
    MAX-ACCESS   read-only
    STATUS       current
    DESCRIPTION
        "Cisco UCS fault:Inst:lastTransition managed object property"
    ::= { cucsFaultEntry 14 }

cucsFaultLc OBJECT-TYPE
    SYNTAX       CucsConditionLifecycle
    MAX-ACCESS   read-only
    STATUS       current
    DESCRIPTION
        "Cisco UCS fault:Inst:lc managed object property"
    ::= { cucsFaultEntry 15 }

cucsFaultOccur OBJECT-TYPE
    SYNTAX       Counter32
    MAX-ACCESS   read-only
    STATUS       current
    DESCRIPTION
        "Cisco UCS fault:Inst:occur managed object property"
    ::= { cucsFaultEntry 16 }

cucsFaultOrigSeverity OBJECT-TYPE
    SYNTAX       CucsFaultSeverity
    MAX-ACCESS   read-only
    STATUS       current
    DESCRIPTION
        "Cisco UCS fault:Inst:origSeverity managed object property"
    ::= { cucsFaultEntry 17 }

cucsFaultPrevSeverity OBJECT-TYPE
    SYNTAX       CucsFaultSeverity
    MAX-ACCESS   read-only
    STATUS       current
    DESCRIPTION
        "Cisco UCS fault:Inst:prevSeverity managed object property"
    ::= { cucsFaultEntry 18 }

cucsFaultRule OBJECT-TYPE
    SYNTAX       CucsConditionRule
    MAX-ACCESS   read-only
    STATUS       current
    DESCRIPTION
        "Cisco UCS fault:Inst:rule managed object property"
    ::= { cucsFaultEntry 19 }

cucsFaultSeverity OBJECT-TYPE
    SYNTAX       CucsFaultSeverity
    MAX-ACCESS   read-only
    STATUS       current
    DESCRIPTION
        "Cisco UCS fault:Inst:severity managed object property"
    ::= { cucsFaultEntry 20 }

cucsFaultTags OBJECT-TYPE
    SYNTAX       CucsConditionTag
    MAX-ACCESS   read-only
    STATUS       current
    DESCRIPTION
        "Cisco UCS fault:Inst:tags managed object property"
    ::= { cucsFaultEntry 21 }

cucsFaultType OBJECT-TYPE
    SYNTAX       CucsFaultType
    MAX-ACCESS   read-only
    STATUS       current
    DESCRIPTION
        "Cisco UCS fault:Inst:type managed object property"
    ::= { cucsFaultEntry 22 }

cucsFaultPolicyTable OBJECT-TYPE
    SYNTAX           SEQUENCE OF CucsFaultPolicyEntry
    MAX-ACCESS       not-accessible
    STATUS           current
    DESCRIPTION
        "Cisco UCS fault:Policy managed object table"
    ::= { cucsFaultObjects 3 }

cucsFaultPolicyEntry OBJECT-TYPE
    SYNTAX           CucsFaultPolicyEntry
    MAX-ACCESS       not-accessible
    STATUS           current
    DESCRIPTION
        "Entry for the cucsFaultPolicyTable table."
    INDEX { cucsFaultPolicyInstanceId }
    ::= { cucsFaultPolicyTable 1 }

CucsFaultPolicyEntry ::= SEQUENCE {
    cucsFaultPolicyInstanceId                                        CucsManagedObjectId,
    cucsFaultPolicyDn                                                CucsManagedObjectDn,
    cucsFaultPolicyRn                                                SnmpAdminString,
    cucsFaultPolicyClearAction                                       CucsFaultPolicyClearAction,
    cucsFaultPolicyClearInterval                                     TimeIntervalSec,
    cucsFaultPolicyDescr                                             SnmpAdminString,
    cucsFaultPolicyFlapInterval                                      Unsigned64,
    cucsFaultPolicyIntId                                             SnmpAdminString,
    cucsFaultPolicyName                                              SnmpAdminString,
    cucsFaultPolicyRetentionInterval                                 TimeIntervalSec,
    cucsFaultPolicySizeLimit                                         Gauge32
}

cucsFaultPolicyInstanceId OBJECT-TYPE
    SYNTAX       CucsManagedObjectId
    MAX-ACCESS   not-accessible
    STATUS       current
    DESCRIPTION
        "Instance identifier of the managed object."
    ::= { cucsFaultPolicyEntry 1 }

cucsFaultPolicyDn OBJECT-TYPE
    SYNTAX       CucsManagedObjectDn
    MAX-ACCESS   read-only
    STATUS       current
    DESCRIPTION
        "Cisco UCS fault:Policy:dn managed object property"
    ::= { cucsFaultPolicyEntry 2 }

cucsFaultPolicyRn OBJECT-TYPE
    SYNTAX       SnmpAdminString
    MAX-ACCESS   read-only
    STATUS       current
    DESCRIPTION
        "Cisco UCS fault:Policy:rn managed object property"
    ::= { cucsFaultPolicyEntry 3 }

cucsFaultPolicyClearAction OBJECT-TYPE
    SYNTAX       CucsFaultPolicyClearAction
    MAX-ACCESS   read-only
    STATUS       current
    DESCRIPTION
        "Cisco UCS fault:Policy:clearAction managed object property"
    ::= { cucsFaultPolicyEntry 4 }

cucsFaultPolicyClearInterval OBJECT-TYPE
    SYNTAX       TimeIntervalSec
    MAX-ACCESS   read-only
    STATUS       current
    DESCRIPTION
        "Cisco UCS fault:Policy:clearInterval managed object property"
    ::= { cucsFaultPolicyEntry 5 }

cucsFaultPolicyDescr OBJECT-TYPE
    SYNTAX       SnmpAdminString
    MAX-ACCESS   read-only
    STATUS       current
    DESCRIPTION
        "Cisco UCS fault:Policy:descr managed object property"
    ::= { cucsFaultPolicyEntry 6 }

cucsFaultPolicyFlapInterval OBJECT-TYPE
    SYNTAX       Unsigned64
    MAX-ACCESS   read-only
    STATUS       current
    DESCRIPTION
        "Cisco UCS fault:Policy:flapInterval managed object property"
    ::= { cucsFaultPolicyEntry 7 }

cucsFaultPolicyIntId OBJECT-TYPE
    SYNTAX       SnmpAdminString
    MAX-ACCESS   read-only
    STATUS       current
    DESCRIPTION
        "Cisco UCS fault:Policy:intId managed object property"
    ::= { cucsFaultPolicyEntry 8 }

cucsFaultPolicyName OBJECT-TYPE
    SYNTAX       SnmpAdminString
    MAX-ACCESS   read-only
    STATUS       current
    DESCRIPTION
        "Cisco UCS fault:Policy:name managed object property"
    ::= { cucsFaultPolicyEntry 9 }

cucsFaultPolicyRetentionInterval OBJECT-TYPE
    SYNTAX       TimeIntervalSec
    MAX-ACCESS   read-only
    STATUS       current
    DESCRIPTION
        "Cisco UCS fault:Policy:retentionInterval managed object property"
    ::= { cucsFaultPolicyEntry 10 }

cucsFaultPolicySizeLimit OBJECT-TYPE
    SYNTAX       Gauge32
    MAX-ACCESS   read-only
    STATUS       current
    DESCRIPTION
        "Cisco UCS fault:Policy:sizeLimit managed object property"
    ::= { cucsFaultPolicyEntry 11 }

END
