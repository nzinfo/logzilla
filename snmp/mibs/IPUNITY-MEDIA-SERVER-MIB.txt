--
-- MIB File for IP Unity Media Server 
-- $Id: IpUnity.mib,v 1.118 2008/08/20 14:49:05 harishn Exp $ 
--
--
--

IPUNITY-MEDIA-SERVER-MIB DEFINITIONS ::= BEGIN

IMPORTS  
	enterprises,
	MODULE-IDENTITY,
	OBJECT-TYPE,
	Integer32,
	Counter32,
	IpAddress,
	NOTIFICATION-TYPE
		FROM SNMPv2-SMI
	DisplayString,
	RowStatus
		FROM SNMPv2-TC
	ifIndex
		FROM RFC1213-MIB;

ipUnityMediaServer      MODULE-IDENTITY
    LAST-UPDATED "0408272000Z"  -- 2004, Aug 26 8.00PM GMT
    ORGANIZATION "IP Unity Inc."
    CONTACT-INFO
                 "Technical Support

                Postal: IP Unity Inc.
                        475 Sycamore Drive, Milpitas, CA 95035

                Tel:    1-408-582-1100
                E-Mail: techsupport@ip-unity.com"
    DESCRIPTION
        "The MIB tree for IP Unity under the enterprises node. It describes the 
	IP Unity Proprietary Information in order to manage the IP Unity Media Server."
    ::= { ipunity 1 }

ipunity     OBJECT IDENTIFIER ::= { enterprises 5134 }

-- Textual conventions 

SccIfType ::= TEXTUAL-CONVENTION
	STATUS current
    DESCRIPTION
		"Interface type for SCC card."
    SYNTAX INTEGER { other (0),
    				 signal-media (1), 
    				 file-system (2),
    				 management (3), 
    				 signal-cp-only (4), 
    				 signal-application-only (5) 
    } 
    
Language ::= TEXTUAL-CONVENTION
	STATUS current
    DESCRIPTION
		"Possible languages"
    SYNTAX INTEGER { 
    	english (1), 
    	chinese (2), 
    	spanish (3),
    	japanese (4),
    	french (5),
    	russian (6),
        german (7),
        swedish (8),
        malay (9),
        tamil (10),
        dutch (11)
    }
    
ITUAdminState ::= TEXTUAL-CONVENTION
	STATUS current
    DESCRIPTION
		"Represents the various possible administrative states (ITU-T X.731)"
    SYNTAX INTEGER { 
    	locked (0), 
       	unlocked (1),
    	shuttingDown (2) 
    }

ITUOperState ::= TEXTUAL-CONVENTION
	STATUS current
    DESCRIPTION
		"Represents the various possible operational states (ITU-T X.731)"
    SYNTAX INTEGER { 
    	disabled (0), 
       	enabled (1)
	}

ITUUsageState ::= TEXTUAL-CONVENTION
	STATUS current
    DESCRIPTION
		"Represents the various possible usage states (ITU-T X.731)"
    SYNTAX INTEGER { 
    	idle (0), 
       	active (1),
       	busy (2),
       	initializing (3),
       	init-failed (4),
       	enabling (5),
       	disabling (6),
       	annc-download (7)
	}

ITUAvailabilityStatus ::= TEXTUAL-CONVENTION
	STATUS current
    DESCRIPTION
		"Represents the various possible availability status values
		(ITU-T X.731)."
    SYNTAX INTEGER { 
		not-installed(0),
		installed(1),
		in-test(2),
		power-off(3),
		off-duty(4),
		in-sync(5),
		init-failed(6)
	}
	
ITUStandbyStatus ::= TEXTUAL-CONVENTION
	STATUS current
    DESCRIPTION
		"Represents the various possible standby status values
		(ITU-T X.731)."
    SYNTAX INTEGER {
		not-applicapble(0),
		not-available (1),
		providing-service (2),
		cold-standby (3),
		hot-standby (4),
		warm-standby (5)
	}
	
MtceAdminCommand ::= TEXTUAL-CONVENTION
	STATUS current
    DESCRIPTION
		"Used for providing the administration related maintenance 
		command."
    SYNTAX INTEGER {
                no-command (0),
		lock-graceful (1),
		lock-force (2),
		unlock (3),
		reset (4)     
	}

MtceAdminCommandStatus ::= TEXTUAL-CONVENTION
	STATUS current
    DESCRIPTION
		"Used for providing the result of MtceAdminCommand."
    SYNTAX INTEGER {
		null (0),
		in-progress (1),
		success (2),     
		failed (3),
		rejected (4)
	}					        

LanguageBitMap ::= TEXTUAL-CONVENTION
	STATUS current
    DESCRIPTION
		"Used for providing the bit map representation of the language supported.
		It will be represented in the 2 power n values based on the languages.
		Following are the currently supported value.
                1 ------ none
		2(2^1) - English
		4(2^2) - Chinese
	        8(2^3) - Spanish	
		16(2^4) - Japanese
	        32(2^5) - French	
		64(2^6) - Russian
	        128(2^7) - German	
	        256(2^8) - Swedish	
	        512(2^9) - Malay	
		1024(2^10) - Tamil
	        2048(2^11) - Dutch."
    SYNTAX Integer32	

IPv6SupportIfType ::= TEXTUAL-CONVENTION
	STATUS current
    DESCRIPTION
		"Interface type support for IPv6."
    SYNTAX INTEGER { 
    				 signal-media (1)
    } 
    
-- Type definitions for card , bank , module , channel numbers

IpUnityCardNo  		::= INTEGER (0..9 | 0..3)
IpUnityBankNo		::= INTEGER (0..3)
IpUnityModuleNo		::= INTEGER (0..7)
IpUnityChannelNo	::= INTEGER (0..31)

-- OBJECT IDENTIFIER Definitions:

ipUnityMSConfigMib      	OBJECT IDENTIFIER ::= { ipUnityMediaServer 1 }
ipUnityStatistics       	OBJECT IDENTIFIER ::= { ipUnityMediaServer 2 }
ipUnityMaintenanceGroup    	OBJECT IDENTIFIER ::= { ipUnityMediaServer 3 }
ipUnityNotificationPrefix	OBJECT IDENTIFIER ::= { ipUnityMediaServer 4 }
ipUnityTrapRelatedVariables	OBJECT IDENTIFIER ::= { ipUnityMediaServer 5 } 
msConfigurationObjects		OBJECT IDENTIFIER ::= { ipUnityMediaServer 6 }
msSecurityObjects		OBJECT IDENTIFIER ::= { ipUnityMediaServer 7 }
ipUnityBannerGroup		OBJECT IDENTIFIER ::= { ipUnityMediaServer 8 }
ipUnitySoftwareLicenseGroup	OBJECT IDENTIFIER ::= { ipUnityMediaServer 9 }

ipUnityNotifications		OBJECT IDENTIFIER ::= { ipUnityNotificationPrefix 0 }

-- IP Unity Media Server Configuration MIB objects   
-- Obsoleting this entire group. 
-- All the configuration objects will be present in 
-- msConfigurationObjects group with proper hierarchy for Media Server release 2.7 onwards.

-- ipUnityMSConfigMib is OBSOLETE
-- ipSecEthernetModeTable is OBSOLETE and is replaced with ipSecEtherModeTable



-- the IP Unity card table

ipUnityCardTable OBJECT-TYPE
	SYNTAX SEQUENCE OF IpUnityCardEntry
	MAX-ACCESS not-accessible
	STATUS current
	DESCRIPTION
		"A table containing information for each card in the Media Server.
		An entry will be present whether the card is present in the slot
		or not."
	::= { ipUnityMaintenanceGroup 1 }

ipUnityCardEntry OBJECT-TYPE
	SYNTAX IpUnityCardEntry
	MAX-ACCESS not-accessible
	STATUS current
	DESCRIPTION
		"An entry in the card table containing information about a
		particular card."
    INDEX { ipUnityCardIndex }
	::= { ipUnityCardTable  1 }

IpUnityCardEntry ::= SEQUENCE {
	ipUnityCardIndex				IpUnityCardNo,
	ipUnityCardType					INTEGER,
	ipUnityCardAdminState			ITUAdminState,
	ipUnityCardOperState			ITUOperState,
	ipUnityCardUsageState			ITUUsageState,
	ipUnityCardAvailabilityStatus	ITUAvailabilityStatus,
	ipUnityCardStandbyStatus		ITUStandbyStatus,
	ipUnityCardNumCriticalAlarms	INTEGER,
	ipUnityCardNumMajorAlarms		INTEGER,
	ipUnityCardNumMinorAlarms		INTEGER,
	ipUnityCardManfacType			INTEGER,
	ipUnityCardAdminCommand			MtceAdminCommand,
	ipUnityCardAdminCommandStatus	MtceAdminCommandStatus,
	ipUnityCardAdminCmdFailureReason	DisplayString,
	ipUnityCardCpuUsage			INTEGER,
	ipUnityCardMemUsage			INTEGER,
	ipUnityCardAvgCpuUsage			INTEGER,
	ipUnityCardAvgMemUsage			INTEGER
}

ipUnityCardIndex OBJECT-TYPE
	SYNTAX IpUnityCardNo
	MAX-ACCESS read-only
	STATUS current
	DESCRIPTION
		"Represents the Card number."
	::= {ipUnityCardEntry 1 }

ipUnityCardType OBJECT-TYPE
	SYNTAX INTEGER {
		other (0),
		scc (1),
		mpc (2)
	}
	MAX-ACCESS read-only 
	STATUS current
	DESCRIPTION
		"Represents the type of the Card. This is the basic card type.
		Manufacturing type of the card gives the actual hardware type for
		the card."
	::= {ipUnityCardEntry 2 }

ipUnityCardAdminState OBJECT-TYPE
	SYNTAX ITUAdminState
	MAX-ACCESS read-only
	STATUS current
	DESCRIPTION
		"Represents the current ITU administrative state of the Card."
	::= {ipUnityCardEntry 3 }

ipUnityCardOperState OBJECT-TYPE
	SYNTAX ITUOperState
	MAX-ACCESS read-only
	STATUS current
	DESCRIPTION
		"Represents the current ITU operational state of the Card."
	::= {ipUnityCardEntry 4 }
		
ipUnityCardUsageState OBJECT-TYPE
	SYNTAX ITUUsageState
	MAX-ACCESS read-only
	STATUS current
	DESCRIPTION
		"Represents the current ITU usage state of the Card."
	::= {ipUnityCardEntry 5 }

ipUnityCardAvailabilityStatus OBJECT-TYPE
	SYNTAX ITUAvailabilityStatus
	MAX-ACCESS read-only
	STATUS current
	DESCRIPTION
		"Represents the current ITU availability status of the card."
	::= {ipUnityCardEntry 6 }
        
ipUnityCardStandbyStatus OBJECT-TYPE
	SYNTAX ITUStandbyStatus
	MAX-ACCESS read-only
	STATUS current
	DESCRIPTION
		"Represents the current ITU standby status of the card."
	::= {ipUnityCardEntry 7 }

ipUnityCardNumCriticalAlarms OBJECT-TYPE
	SYNTAX INTEGER	(0..65535)
	MAX-ACCESS read-only
	STATUS current
	DESCRIPTION
		"Represents the number of critical alarms generated by this card."
	::= {ipUnityCardEntry 8 }
        
ipUnityCardNumMajorAlarms OBJECT-TYPE
	SYNTAX INTEGER	(0..65535)
	MAX-ACCESS read-only
	STATUS current
	DESCRIPTION
		" Represents the number of major alarms generated by this card."
	::= {ipUnityCardEntry 9 }
        
ipUnityCardNumMinorAlarms OBJECT-TYPE
	SYNTAX INTEGER	(0..65535)
	MAX-ACCESS read-only
	STATUS current
	DESCRIPTION
		"Represents the number of minor alarms generated by this card."
	::= {ipUnityCardEntry 10 }
	
ipUnityCardManfacType OBJECT-TYPE
	SYNTAX INTEGER {
		other (0),
		mpc1 (1),
		mpc2 (2),
		mpc4 (4),
		spm (5),
		scc1 (10),
		mpc11 (11),
		mpc12 (12),
		mpc14 (14),
		mpc15 (15),
		mpc16 (16),
		mpc17 (17),
		mpc18 (18),
		scc2 (20),
		scc3 (30),
		mpc20 (31)
	}
	MAX-ACCESS read-only
	STATUS current
	DESCRIPTION
		"Gives the manufacturing type for the card."
	::= {ipUnityCardEntry 11 } 	

ipUnityCardAdminCommand OBJECT-TYPE
	SYNTAX MtceAdminCommand
	MAX-ACCESS read-write
	STATUS current
	DESCRIPTION
		"Used by the adminstrator to lock, unlock or reset the card. Each 
		operation may take good amount of time so the management station needs
		to query the ipUnityCardAdminCommandStatus object to know the result
		of the command set through this object.
		
		At a time only one command is allowed. MediaServer won't accept any
		command until the current command is completed. If management station
		sends another command when the first command is in-progress then Media
		Server rejects the second command immediatley.
		
		For get operation this object returns the last command that has been
		executed for this card through SNMP interface."
	::= {ipUnityCardEntry 12 }

ipUnityCardAdminCommandStatus OBJECT-TYPE
	SYNTAX MtceAdminCommandStatus
	MAX-ACCESS read-only
	STATUS current
	DESCRIPTION
		"Status of the command ipUnityCardAdminCommand."
	::= {ipUnityCardEntry 13 }	

ipUnityCardAdminCmdFailureReason OBJECT-TYPE
	SYNTAX DisplayString
	MAX-ACCESS read-only
	STATUS current
	DESCRIPTION
		"Result of the command ipUnityCardAdminCommand. This value
                 is to give extra error information on why ipUnityCardAdminCommand
                 is failed. "
	::= {ipUnityCardEntry 14 }		

ipUnityCardCpuUsage OBJECT-TYPE
    SYNTAX INTEGER
	MAX-ACCESS read-only
	STATUS current
	DESCRIPTION
		"Cpu Usage by this card.The value -1 indicates invalid usage."
	::= {ipUnityCardEntry 15 }

ipUnityCardMemUsage OBJECT-TYPE
	SYNTAX INTEGER
	MAX-ACCESS read-only
	STATUS current
	DESCRIPTION
		"Memory Usage by this card.The value -1 indicates invalid usage."
	::= {ipUnityCardEntry 16 }

ipUnityCardAvgCpuUsage OBJECT-TYPE
	SYNTAX INTEGER
	MAX-ACCESS read-only
	STATUS current
	DESCRIPTION
		"Average CPU usage by this card.The value -1 indicates invalid usage."
	::= {ipUnityCardEntry 17 }

ipUnityCardAvgMemUsage OBJECT-TYPE
	SYNTAX INTEGER
	MAX-ACCESS read-only
	STATUS current
	DESCRIPTION
		"Average Memory usage by this card.The value -1 indicates invalid usage."
	::= {ipUnityCardEntry 18 }

-- the IP Unity bank table 

ipUnityBankTable OBJECT-TYPE
	SYNTAX SEQUENCE OF IpUnityBankEntry
	MAX-ACCESS not-accessible
	STATUS current
	DESCRIPTION
		" A table containing information about each ODSP bank in the 
		Media Server." 
	::= { ipUnityMaintenanceGroup 2 }

ipUnityBankEntry  OBJECT-TYPE
	SYNTAX IpUnityBankEntry
	MAX-ACCESS not-accessible
	STATUS current
	DESCRIPTION
		"An entry in the bank table containing information about the current 
		status of the bank."
	INDEX { ipUnityCardIndex, ipUnityBankIndex }
	::= { ipUnityBankTable  1 }

IpUnityBankEntry ::= SEQUENCE {
	ipUnityBankIndex      			IpUnityBankNo,
	ipUnityBankType					INTEGER,
	ipUnityBankAddress       		IpAddress,
	ipUnityBankAdminState 			ITUAdminState,
	ipUnityBankOperState 			ITUOperState,
	ipUnityBankUsageState			ITUUsageState,
	ipUnityBankAvailabilityStatus	ITUAvailabilityStatus,
	ipUnityBankNumCriticalAlarms	INTEGER,
	ipUnityBankNumMajorAlarms		INTEGER,
	ipUnityBankNumMinorAlarms		INTEGER,
	ipUnityBankOdspImageVersion		DisplayString,
	ipUnityBankAdminCommand			MtceAdminCommand,
	ipUnityBankAdminCommandStatus	MtceAdminCommandStatus,
	ipUnityBankAdminCmdFailureReason	DisplayString,
	ipUnityBankCpuUsage			INTEGER,
	ipUnityBankMemUsage			INTEGER,
	ipUnityBankAvgCpuUsage			INTEGER,
	ipUnityBankAvgMemUsage			INTEGER
}

ipUnityBankIndex  OBJECT-TYPE
        SYNTAX IpUnityBankNo
        MAX-ACCESS read-only
        STATUS current
        DESCRIPTION
                "Represents the bank number."
        ::= {ipUnityBankEntry 1 }

ipUnityBankType OBJECT-TYPE
	SYNTAX INTEGER {
		unknown (0),
		odsp (1),
		odsp2 (2),
		spm (3)
	}
	MAX-ACCESS read-only 
	STATUS current
	DESCRIPTION
		"Represents the type of the bank."
	::= {ipUnityBankEntry 2 }

ipUnityBankAddress OBJECT-TYPE
	SYNTAX IpAddress
	MAX-ACCESS read-only
	STATUS current
	DESCRIPTION
		"Represents the IP address of the bank."
	::= {ipUnityBankEntry 3 }

ipUnityBankAdminState OBJECT-TYPE
	SYNTAX ITUAdminState
	MAX-ACCESS read-only
	STATUS current
	DESCRIPTION
		"Represents the current ITU administrative state of the Bank."
	::= {ipUnityBankEntry 4 }

ipUnityBankOperState OBJECT-TYPE
	SYNTAX ITUOperState
	MAX-ACCESS read-only
	STATUS current
	DESCRIPTION
		"Represents the current ITU operational state of the Bank."
	::= {ipUnityBankEntry 5 }
		
ipUnityBankUsageState OBJECT-TYPE
	SYNTAX ITUUsageState
	MAX-ACCESS read-only
	STATUS current
	DESCRIPTION
		"Represents the current ITU usage state of the Bank."
	::= {ipUnityBankEntry 6 }

ipUnityBankAvailabilityStatus OBJECT-TYPE
	SYNTAX ITUAvailabilityStatus
	MAX-ACCESS read-only
	STATUS current
	DESCRIPTION
		"Represents the current ITU availability status of the bank."
	::= {ipUnityBankEntry 7 }
        
ipUnityBankNumCriticalAlarms OBJECT-TYPE
	SYNTAX INTEGER	(0..65535)
	MAX-ACCESS read-only
	STATUS current
	DESCRIPTION
		" Represents the number of critical alarms generated by this bank."
	::= {ipUnityBankEntry 8 }
        
ipUnityBankNumMajorAlarms OBJECT-TYPE
	SYNTAX INTEGER	(0..65535)
	MAX-ACCESS read-only
	STATUS current
	DESCRIPTION
		" Represents the number of major alarms generated by this bank."
	::= {ipUnityBankEntry 9 }
        
ipUnityBankNumMinorAlarms OBJECT-TYPE
	SYNTAX INTEGER	(0..65535)
	MAX-ACCESS read-only
	STATUS current
	DESCRIPTION
		" Represents the number of minor alarms generated by this bank."
	::= {ipUnityBankEntry 10 }
        
ipUnityBankOdspImageVersion OBJECT-TYPE
	SYNTAX DisplayString
	MAX-ACCESS read-only
	STATUS obsolete
	DESCRIPTION
		"Represents the version of the software image running in the bank."
	::= {ipUnityBankEntry 11 }

ipUnityBankAdminCommand OBJECT-TYPE
	SYNTAX MtceAdminCommand
	MAX-ACCESS read-write
	STATUS current
	DESCRIPTION
		"Used by the adminstrator to lock, unlock or reset the bank. Each 
		operation may take good amount of time so the management station needs
		to query the ipUnityBankAdminCommandStatus object to know the result
		of the command set through this object.
		
		At a time only one command is allowed. MediaServer won't accept any
		command until the current command is completed. If management station
		sends another command when the first command is in-progress then Media
		Server rejects the second command immediatley.
		
		For get operation this object returns the last command that has been
		executed for this card through SNMP interface."
	::= {ipUnityBankEntry 12 }

ipUnityBankAdminCommandStatus OBJECT-TYPE
	SYNTAX MtceAdminCommandStatus
	MAX-ACCESS read-only
	STATUS current
	DESCRIPTION
		"Status of the command ipUnityBankAdminCommand."
	::= {ipUnityBankEntry 13 }		

ipUnityBankAdminCmdFailureReason OBJECT-TYPE
	SYNTAX DisplayString
	MAX-ACCESS read-only
	STATUS current
	DESCRIPTION
		"Result of the command ipUnityBankAdminCommand. This value
                 is to give extra error information on why ipUnityBankAdminCommand
                 is failed."
	::= {ipUnityBankEntry 14 }		

ipUnityBankCpuUsage OBJECT-TYPE
	SYNTAX INTEGER
	MAX-ACCESS read-only
	STATUS current
	DESCRIPTION
		"Cpu Usage by this Bank.The value -1 indicates invalid usage."
	::= {ipUnityBankEntry 15 }

ipUnityBankMemUsage OBJECT-TYPE
	SYNTAX INTEGER
	MAX-ACCESS read-only
	STATUS current
	DESCRIPTION
		"Memory Usage by this Bank.The value -1 indicates invalid usage."
	::= {ipUnityBankEntry 16 }

ipUnityBankAvgCpuUsage OBJECT-TYPE
	SYNTAX INTEGER
	MAX-ACCESS read-only
	STATUS current
	DESCRIPTION
		"Average CPU usage by this Bank.The value -1 indicates invalid usage."
	::= {ipUnityBankEntry 17 }

ipUnityBankAvgMemUsage OBJECT-TYPE
	SYNTAX INTEGER
	MAX-ACCESS read-only
	STATUS current
	DESCRIPTION
		"Average Memory usage by this Bank.The value -1 indicates invalid usage."
	::= {ipUnityBankEntry 18 }

-- the IP Unity module table

ipUnityModuleTable OBJECT-TYPE
	SYNTAX SEQUENCE OF IpUnityModuleEntry
	MAX-ACCESS not-accessible
	STATUS current
	DESCRIPTION
		"A table containing information on the DSP module configuration in a bank 
		in the Media Server."
	::= { ipUnityMaintenanceGroup 3 }

ipUnityModuleEntry OBJECT-TYPE
    SYNTAX IpUnityModuleEntry
    MAX-ACCESS not-accessible
    STATUS current
    DESCRIPTION
		"An entry in the module table containing information about the current 
		configuration of the module."
    INDEX { ipUnityCardIndex, ipUnityBankIndex, ipUnityModuleIndex }
    ::= { ipUnityModuleTable  1 }

IpUnityModuleEntry ::= SEQUENCE {
	ipUnityModuleIndex      		IpUnityModuleNo,
	ipUnityModuleAdminState 		ITUAdminState,
	ipUnityModuleOperState 			ITUOperState,
	ipUnityModuleUsageState			ITUUsageState,
	ipUnityModuleAvailabilityStatus	ITUAvailabilityStatus,
	ipUnityModuleNumCriticalAlarms	INTEGER,
	ipUnityModuleNumMajorAlarms		INTEGER,
	ipUnityModuleNumMinorAlarms		INTEGER,
	ipUnityModuleDspImageVersion	DisplayString,
	ipUnityModuleAppType 			INTEGER,
	ipUnityModuleAdminCommand		MtceAdminCommand,
	ipUnityModuleAdminCommandStatus	MtceAdminCommandStatus,
	ipUnityModuleAdminCmdFailureReason	DisplayString,
    ipUnityModuleCpuUsage         INTEGER,
    ipUnityModuleMemUsage         INTEGER,
    ipUnityModuleAvgCpuUsage          INTEGER,
    ipUnityModuleAvgMemUsage          INTEGER
}

ipUnityModuleIndex OBJECT-TYPE
	SYNTAX IpUnityModuleNo
	MAX-ACCESS read-only
	STATUS current
	DESCRIPTION
		"Represents the module number."
	::= {ipUnityModuleEntry 1 }

ipUnityModuleAdminState OBJECT-TYPE
	SYNTAX ITUAdminState
	MAX-ACCESS read-only
	STATUS current
	DESCRIPTION
		"Represents the current ITU administrative state of the Module."
	::= {ipUnityModuleEntry 2 }

ipUnityModuleOperState OBJECT-TYPE
	SYNTAX ITUOperState
	MAX-ACCESS read-only
	STATUS current
	DESCRIPTION
		"Represents the current ITU operational state of the Module."
	::= {ipUnityModuleEntry 3 }
		
ipUnityModuleUsageState OBJECT-TYPE
	SYNTAX ITUUsageState
	MAX-ACCESS read-only
	STATUS current
	DESCRIPTION
		"Represents the current ITU usage state of the Module."
	::= {ipUnityModuleEntry 4 }

ipUnityModuleAvailabilityStatus	OBJECT-TYPE
	SYNTAX ITUAvailabilityStatus
	MAX-ACCESS read-only
	STATUS current
	DESCRIPTION
		" Represents the current ITU availability status of the module. "
	::= {ipUnityModuleEntry 5 }
        
ipUnityModuleNumCriticalAlarms	OBJECT-TYPE
	SYNTAX INTEGER	(0..65535)
	MAX-ACCESS read-only
	STATUS current
	DESCRIPTION
		" Represents the number of critical alarms generated by this module."
	::= {ipUnityModuleEntry 6 }

ipUnityModuleNumMajorAlarms	OBJECT-TYPE
	SYNTAX INTEGER	(0..65535)
	MAX-ACCESS read-only
	STATUS current
	DESCRIPTION
		" Represents the number of major alarms generated by this module."
	::= {ipUnityModuleEntry 7 }
        
ipUnityModuleNumMinorAlarms	OBJECT-TYPE
	SYNTAX INTEGER	(0..65535)
	MAX-ACCESS read-only
	STATUS current
	DESCRIPTION
		" Represents the number of minor alarms generated by this module."
	::= {ipUnityModuleEntry 8 }
        
ipUnityModuleDspImageVersion OBJECT-TYPE
	SYNTAX DisplayString
	MAX-ACCESS read-only
	STATUS current
	DESCRIPTION
		"Gives the application image version."
	::= {ipUnityModuleEntry 9 }

ipUnityModuleAppType OBJECT-TYPE
	SYNTAX INTEGER {
		unknown (0),
		dsp (1),
		dsp2 (2),
		asr (3),
		vxml (4),
		http (5),
		scc-cp (6),
		asr-icm (7)
	}
	MAX-ACCESS read-only
	STATUS current
	DESCRIPTION
		"Gives the application type for this module."
	::= {ipUnityModuleEntry 10 }	
	
ipUnityModuleAdminCommand OBJECT-TYPE
	SYNTAX MtceAdminCommand
	MAX-ACCESS read-write
	STATUS current
	DESCRIPTION
		"Used by the adminstrator to lock, unlock or reset the module. Each 
		operation may take good amount of time so the management station needs
		to query the ipUnityBankAdminCommandStatus object to know the result
		of the command set through this object.
		
		At a time only one command is allowed. MediaServer won't accept any
		command until the current command is completed. If management station
		sends another command when the first command is in-progress then Media
		Server rejects the second command immediatley.
		
		For get operation this object returns the last command that has been
		executed for this card through SNMP interface."
	::= {ipUnityModuleEntry 11 }

ipUnityModuleAdminCommandStatus OBJECT-TYPE
	SYNTAX MtceAdminCommandStatus
	MAX-ACCESS read-only
	STATUS current
	DESCRIPTION
		"Status of the command ipUnityModuleAdminCommand."
	::= {ipUnityModuleEntry 12 }		
	
ipUnityModuleAdminCmdFailureReason OBJECT-TYPE
	SYNTAX DisplayString
	MAX-ACCESS read-only
	STATUS current
	DESCRIPTION
		"Result of the command ipUnityModuleAdminCommand. This value
                 is to give extra error information on why ipUnityModuleAdminCommand
                 is failed. "
	::= {ipUnityModuleEntry 13 }		

ipUnityModuleCpuUsage OBJECT-TYPE
    SYNTAX INTEGER
    MAX-ACCESS read-only
    STATUS current
    DESCRIPTION
        "Cpu Usage by this Module. The value -1 indicates invalid usage."
    ::= {ipUnityModuleEntry 14 }

ipUnityModuleMemUsage OBJECT-TYPE
    SYNTAX INTEGER
    MAX-ACCESS read-only
    STATUS current
    DESCRIPTION
        "Memory Usage by this Module.The value -1 indicates invalid usage."
    ::= {ipUnityModuleEntry 15 }

ipUnityModuleAvgCpuUsage OBJECT-TYPE
    SYNTAX INTEGER
    MAX-ACCESS read-only
    STATUS current
    DESCRIPTION
        "Average CPU usage by this Module.The value -1 indicates invalid usage."
    ::= {ipUnityModuleEntry 16 }

ipUnityModuleAvgMemUsage OBJECT-TYPE
    SYNTAX INTEGER
    MAX-ACCESS read-only
    STATUS current
    DESCRIPTION
        "Average Memory usage by this Module.The value -1 indicates invalid usage."
    ::= {ipUnityModuleEntry 17 }

-- the IP Unity DSP channel table
ipUnityChannelTable OBJECT-TYPE
	SYNTAX SEQUENCE OF IpUnityChannelEntry
	MAX-ACCESS not-accessible
	STATUS current
	DESCRIPTION
		"A table containing information on the channel configuration in a DSP 
		module in the Media Server."
	::= { ipUnityMaintenanceGroup 4 }

ipUnityChannelEntry  OBJECT-TYPE
	SYNTAX IpUnityChannelEntry
	MAX-ACCESS not-accessible
	STATUS current
	DESCRIPTION
		"An entry in the channel table containing information about the 
		channel."
    INDEX { ipUnityCardIndex, 
    		ipUnityBankIndex, 
    		ipUnityModuleIndex, 
    		ipUnityChannelIndex 
    }
    ::= { ipUnityChannelTable  1 }

IpUnityChannelEntry ::= SEQUENCE {
   ipUnityChannelIndex	IpUnityChannelNo,
   ipUnityChannelState	INTEGER
}

ipUnityChannelIndex  OBJECT-TYPE
	SYNTAX IpUnityChannelNo
	MAX-ACCESS read-only
	STATUS current
	DESCRIPTION
		"Represents the channel number."
	::= {ipUnityChannelEntry 1 }

ipUnityChannelState OBJECT-TYPE
	SYNTAX INTEGER {
		disabled (0),
		idle (1),
		busy (2),
		reserved (3),
		lockUp (4)
	}
	MAX-ACCESS read-only 
	STATUS current
	DESCRIPTION
		"Gives the state of the channel."
	::= {ipUnityChannelEntry 2 }

msMtceObjects		OBJECT IDENTIFIER ::= { ipUnityMaintenanceGroup 5 }
msVersionObjects	OBJECT IDENTIFIER ::= { ipUnityMaintenanceGroup 6 }
msUpgradeObjects	OBJECT IDENTIFIER ::= { ipUnityMaintenanceGroup 7 }	
ipUnityMSChassisObjects	OBJECT IDENTIFIER ::= { ipUnityMaintenanceGroup 8 }	

-- some Media Server maintainance objects
msMtceAudit OBJECT-TYPE
	SYNTAX INTEGER {
		off (0),
		on (1)
	}
	MAX-ACCESS read-write
	STATUS current
	DESCRIPTION
		"Used to set audit off or on."
	::= { msMtceObjects 1 }
	
msMtceSysCommand OBJECT-TYPE
	SYNTAX INTEGER {
		no-command (0),
		reset (1),
		shutDown (2),
		switchover (3)
	}
	MAX-ACCESS read-write
	STATUS current
	DESCRIPTION
		"Supported commands are reset, shutDown and switchover. For Get request it 
                 returns no-command(0)."
	::= { msMtceObjects 2 }

msMtceSccStandbyCommand OBJECT-TYPE
	SYNTAX INTEGER {
		no-command (0),
		shutDown (1)
	}
	MAX-ACCESS read-write
	STATUS current
	DESCRIPTION
		"Used for shutDown the standby SCC. For Get request it returns no-command(0)."
	::= { msMtceObjects 3 }

msMtceSccSyncCommand OBJECT-TYPE
	SYNTAX INTEGER {
		no-command (0),
		configuration (1),
		audio-files (2),
		images (3)
	}
	MAX-ACCESS read-write
	STATUS current
	DESCRIPTION
		"Synchronization command and its options. For Get request it returns no-command(0)."
	::= { msMtceObjects 4 }

msMtceTerminateCommand OBJECT-TYPE
	SYNTAX INTEGER {
		no-command (0),
		rlogin (1),
		telnet (2)
	}
	MAX-ACCESS read-write
	STATUS current
	DESCRIPTION
		"To terminate rlogin/telnet sessions of the Media Server. For Get request it returns 
                 no-command(0). For telnet(2) it won't terminate the CLI sessions it terminates the
                 telnet sessions for ports otherthan 23."
	::= { msMtceObjects 5 }		

msMtceCommandFailureReason OBJECT-TYPE
        SYNTAX DisplayString
        MAX-ACCESS read-only
        STATUS current
        DESCRIPTION
                "Failure reason for the last maintainence Command SET by SNMP. The command can be
                 msMtceSccSyncCommand, msMtceTerminateCommand, msMtceSysCommand and
                 msMtceSccStandbyCommand. This string gives the reason for failure."
        ::= { msMtceObjects 6 }

-- version related objects
sccCardVersionTable OBJECT-TYPE
	SYNTAX SEQUENCE OF SccCardVersionEntry
	MAX-ACCESS not-accessible
	STATUS current
	DESCRIPTION
		"A table containing hardware and software version information 
		of SCC cards in the Media Server."
	::= { msVersionObjects 1 }

sccCardVersionEntry  OBJECT-TYPE
	SYNTAX SccCardVersionEntry
	MAX-ACCESS not-accessible
	STATUS current
	DESCRIPTION
		"An entry for each SCC card in the system."
    INDEX { ipUnityCardIndex }
    ::= { sccCardVersionTable 1 }

SccCardVersionEntry ::= SEQUENCE {
	sccCardPLDType		DisplayString,
	sccCardPLDRev		DisplayString,
	sccCardPCBRev		DisplayString,
	sccCardPCBConfig 	DisplayString,
	sccCardMfgDate		DisplayString,
	sccCardSerialNum 	DisplayString,
	sccCardCLEINum		DisplayString,
	sccCardBootCode		DisplayString,
	sccCardImageVersion	DisplayString
}

sccCardPLDType  OBJECT-TYPE
	SYNTAX DisplayString
	MAX-ACCESS read-only
	STATUS current
	DESCRIPTION
		"PLD Type of the SCC Card."
	::= {sccCardVersionEntry 1 }

sccCardPLDRev  OBJECT-TYPE
	SYNTAX DisplayString
	MAX-ACCESS read-only
	STATUS current
	DESCRIPTION
		"PLD revision number of the SCC Card."
	::= {sccCardVersionEntry 2 }

sccCardPCBRev  OBJECT-TYPE
	SYNTAX DisplayString
	MAX-ACCESS read-only
	STATUS current
	DESCRIPTION
		"PCB revision number of the SCC Card."
	::= {sccCardVersionEntry 3 }

sccCardPCBConfig OBJECT-TYPE
	SYNTAX DisplayString
	MAX-ACCESS read-only
	STATUS current
	DESCRIPTION
		"PCB Config version of the SCC Card."
	::= {sccCardVersionEntry 4 }

sccCardMfgDate OBJECT-TYPE
	SYNTAX DisplayString (SIZE(6))
	MAX-ACCESS read-only
	STATUS current
	DESCRIPTION
		"Manufacturing date of the SCC Card. it is in mmddyy format and value
		is always 6 octets."
	::= {sccCardVersionEntry 5 }	
	
sccCardSerialNum  OBJECT-TYPE
	SYNTAX DisplayString
	MAX-ACCESS read-only
	STATUS current
	DESCRIPTION
		"Serial number of the SCC Card."
	::= {sccCardVersionEntry 6 }
	
sccCardCLEINum  OBJECT-TYPE
	SYNTAX DisplayString
	MAX-ACCESS read-only
	STATUS current
	DESCRIPTION
		"CLEI number of the SCC Card."
	::= {sccCardVersionEntry 7 }

sccCardBootCode  OBJECT-TYPE
	SYNTAX DisplayString
	MAX-ACCESS read-only
	STATUS current
	DESCRIPTION
		"Boot code version of the SCC Card."
	::= {sccCardVersionEntry 8 }

sccCardImageVersion  OBJECT-TYPE
	SYNTAX DisplayString
	MAX-ACCESS read-only
	STATUS current
	DESCRIPTION
		"Image version of the SCC Card."
	::= {sccCardVersionEntry 9 }

mpcCardVersionTable OBJECT-TYPE
	SYNTAX SEQUENCE OF MpcCardVersionEntry
	MAX-ACCESS not-accessible
	STATUS current
	DESCRIPTION
		"A table containing hardware and software version information 
		of MPC cards in the Media Server."
	::= { msVersionObjects 2 }

mpcCardVersionEntry  OBJECT-TYPE
	SYNTAX MpcCardVersionEntry
	MAX-ACCESS not-accessible
	STATUS current
	DESCRIPTION
		"An entry for each MPC card in the system."
    INDEX { ipUnityCardIndex }
    ::= { mpcCardVersionTable 1 }

MpcCardVersionEntry ::= SEQUENCE {
	mpcCardPCBRev		DisplayString,
	mpcCardMfgDate		DisplayString,
	mpcCardSerialNum 	DisplayString,
	mpcCardCLEINum		DisplayString,
	mpcCardPICVersion	DisplayString
}

mpcCardPCBRev  OBJECT-TYPE
	SYNTAX DisplayString
	MAX-ACCESS read-only
	STATUS current
	DESCRIPTION
		"PCB revision number of the MPC Card."
	::= {mpcCardVersionEntry 1 }

mpcCardMfgDate OBJECT-TYPE
	SYNTAX DisplayString (SIZE(6))
	MAX-ACCESS read-only
	STATUS current
	DESCRIPTION
		"Manufacturing date of the MPC Card. it is in mmddyy format and value
		is always 6 octets."
	::= {mpcCardVersionEntry 2 }
		
mpcCardSerialNum  OBJECT-TYPE
	SYNTAX DisplayString
	MAX-ACCESS read-only
	STATUS current
	DESCRIPTION
		"Serial number of the MPC Card."
	::= {mpcCardVersionEntry 3 }
	
mpcCardCLEINum  OBJECT-TYPE
	SYNTAX DisplayString
	MAX-ACCESS read-only
	STATUS current
	DESCRIPTION
		"CLEI number of the MPC Card."
	::= {mpcCardVersionEntry 4 }

mpcCardPICVersion  OBJECT-TYPE
	SYNTAX DisplayString
	MAX-ACCESS read-only
	STATUS current
	DESCRIPTION
		"PIC version of the MPC Card."
	::= {mpcCardVersionEntry 5 }

bankVersionTable OBJECT-TYPE
	SYNTAX SEQUENCE OF BankVersionEntry
	MAX-ACCESS not-accessible
	STATUS current
	DESCRIPTION
		"A table containing hardware and software version information 
		of all the banks in the Media Server."
	::= { msVersionObjects 3 }

bankVersionEntry  OBJECT-TYPE
	SYNTAX BankVersionEntry
	MAX-ACCESS not-accessible
	STATUS current
	DESCRIPTION
		"An entry for each bank in the system."
    INDEX { ipUnityCardIndex, ipUnityBankIndex }
    ::= { bankVersionTable 1 }

BankVersionEntry ::= SEQUENCE {
	bankPLDType			DisplayString,
	bankPLDRev			DisplayString,
	bankPCBRev			DisplayString,
	bankPCBConfig 		DisplayString,
	bankMfgDate			DisplayString,
	bankSerialNum 		DisplayString,
	bankCLEINum			DisplayString,
	bank8260BootCode		DisplayString,
	bank8260ImageVersion	DisplayString,
	bankDspVersion		DisplayString
}

bankPLDType  OBJECT-TYPE
	SYNTAX DisplayString
	MAX-ACCESS read-only
	STATUS current
	DESCRIPTION
		"PLD Type of the bank."
	::= {bankVersionEntry 1 }

bankPLDRev  OBJECT-TYPE
	SYNTAX DisplayString
	MAX-ACCESS read-only
	STATUS current
	DESCRIPTION
		"PLD revision number of the bank."
	::= {bankVersionEntry 2 }

bankPCBRev  OBJECT-TYPE
	SYNTAX DisplayString
	MAX-ACCESS read-only
	STATUS current
	DESCRIPTION
		"PCB revision number of the bank."
	::= {bankVersionEntry 3 }

bankPCBConfig OBJECT-TYPE
	SYNTAX DisplayString
	MAX-ACCESS read-only
	STATUS current
	DESCRIPTION
		"PCB Config version of the bank."
	::= {bankVersionEntry 4 }
	
bankMfgDate OBJECT-TYPE
	SYNTAX DisplayString (SIZE(6))
	MAX-ACCESS read-only
	STATUS current
	DESCRIPTION
		"Manufacturing date of the bank. it is in mmddyy format and value
		is always 6 octets."
	::= {bankVersionEntry 5 }	
	
bankSerialNum  OBJECT-TYPE
	SYNTAX DisplayString
	MAX-ACCESS read-only
	STATUS current
	DESCRIPTION
		"Serial number of the bank."
	::= {bankVersionEntry 6 }
	
bankCLEINum  OBJECT-TYPE
	SYNTAX DisplayString
	MAX-ACCESS read-only
	STATUS current
	DESCRIPTION
		"CLEI number of the bank."
	::= {bankVersionEntry 7 }

bank8260BootCode  OBJECT-TYPE
	SYNTAX DisplayString
	MAX-ACCESS read-only
	STATUS current
	DESCRIPTION
		"8260 Boot code version of the bank."
	::= {bankVersionEntry 8 }

bank8260ImageVersion  OBJECT-TYPE
	SYNTAX DisplayString
	MAX-ACCESS read-only
	STATUS current
	DESCRIPTION
		"8260 Image version of the bank."
	::= {bankVersionEntry 9 }

bankDspVersion  OBJECT-TYPE
	SYNTAX DisplayString
	MAX-ACCESS read-only
	STATUS current
	DESCRIPTION
		"DSP Image version of the bank. This object is used only for odsp
		banks. For non odsp banks value will be an empty string."
	::= {bankVersionEntry 10 }	

spmG4VersionTable OBJECT-TYPE
	SYNTAX SEQUENCE OF SpmG4VersionEntry
	MAX-ACCESS not-accessible
	STATUS current
	DESCRIPTION
		"A table containing version information of G4 modules in all the 
		SPM banks of the Media Server. bankVersionTable gives all the
		general version related values and this table gives the version
		information specific to spmg4 modules on the bank."
	::= { msVersionObjects 4 }

spmG4VersionEntry  OBJECT-TYPE
	SYNTAX SpmG4VersionEntry
	MAX-ACCESS not-accessible
	STATUS current
	DESCRIPTION
		"An entry for each SPM bank in the system."
    INDEX { ipUnityCardIndex, ipUnityBankIndex }
    ::= { spmG4VersionTable 1 }

SpmG4VersionEntry ::= SEQUENCE {
   spmG4BootCode			DisplayString,
   spmG4KernelVersion0		DisplayString,
   spmG4AppImageVersion0	DisplayString,
   spmG4KernelVersion1		DisplayString,
   spmG4AppImageVersion1	DisplayString   
}

spmG4BootCode  OBJECT-TYPE
	SYNTAX DisplayString
	MAX-ACCESS read-only
	STATUS current
	DESCRIPTION
		"Version of the G4 boot code for this SPM bank."
	::= {spmG4VersionEntry 1 }

spmG4KernelVersion0  OBJECT-TYPE
	SYNTAX DisplayString
	MAX-ACCESS read-only
	STATUS current
	DESCRIPTION
		"Version of the Kernel for G4-0 (first G4 module in the bank)."
	::= {spmG4VersionEntry 2 }

spmG4AppImageVersion0  OBJECT-TYPE
	SYNTAX DisplayString
	MAX-ACCESS read-only
	STATUS current
	DESCRIPTION
		"Version of the application image for G4-0 (first G4 module in 
		the bank)."
	::= {spmG4VersionEntry 3 }

spmG4KernelVersion1  OBJECT-TYPE
	SYNTAX DisplayString
	MAX-ACCESS read-only
	STATUS current
	DESCRIPTION
		"Version of the Kernel for G4-1 (second G4 module in the bank)."
	::= {spmG4VersionEntry 4 }

spmG4AppImageVersion1  OBJECT-TYPE
	SYNTAX DisplayString
	MAX-ACCESS read-only
	STATUS current
	DESCRIPTION
		"Version of the application image for G4-1 (second G4 module in 
		the bank)."
	::= {spmG4VersionEntry 5 }			

-- Alarm card version information

alarmCardVersionTable OBJECT-TYPE
	SYNTAX SEQUENCE OF AlarmCardVersionEntry
	MAX-ACCESS not-accessible
	STATUS current
	DESCRIPTION
		"A table containing version information of alarm cards in the 
		Media Server."
	::= { msVersionObjects 5 }

alarmCardVersionEntry  OBJECT-TYPE
	SYNTAX AlarmCardVersionEntry
	MAX-ACCESS not-accessible
	STATUS current
	DESCRIPTION
		"An entry for each alarm card in the system."
    INDEX { alarmCardIndex }
    ::= { alarmCardVersionTable 1 }

AlarmCardVersionEntry ::= SEQUENCE {
	alarmCardIndex		Integer32,
	alarmCardPCBRev		DisplayString,
	alarmCardMfgDate	DisplayString,
	alarmCardSerialNum	DisplayString,
	alarmCardCLEINum 	DisplayString,
	alarmCardPICVersion	DisplayString
}

alarmCardIndex  OBJECT-TYPE
	SYNTAX Integer32 (1)
	MAX-ACCESS not-accessible
	STATUS current
	DESCRIPTION
		"Alarm Card number. Currently Media Server supports only one alaram card."
	::= {alarmCardVersionEntry 1 }

alarmCardPCBRev  OBJECT-TYPE
	SYNTAX DisplayString
	MAX-ACCESS read-only
	STATUS current
	DESCRIPTION
		"PCB revision number of the Alarm Card."
	::= {alarmCardVersionEntry 2 }

alarmCardMfgDate OBJECT-TYPE
	SYNTAX DisplayString (SIZE(6))
	MAX-ACCESS read-only
	STATUS current
	DESCRIPTION
		"Manufacturing date of the Alarm Card. it is in mmddyy format and value
		is always 6 octets."
	::= {alarmCardVersionEntry 3 }
		
alarmCardSerialNum  OBJECT-TYPE
	SYNTAX DisplayString
	MAX-ACCESS read-only
	STATUS current
	DESCRIPTION
		"Serial number of the Alarm Card."
	::= {alarmCardVersionEntry 4 }
	
alarmCardCLEINum  OBJECT-TYPE
	SYNTAX DisplayString
	MAX-ACCESS read-only
	STATUS current
	DESCRIPTION
		"CLEI number of the Alarm Card."
	::= {alarmCardVersionEntry 5 }

alarmCardPICVersion  OBJECT-TYPE
	SYNTAX DisplayString
	MAX-ACCESS read-only
	STATUS current
	DESCRIPTION
		"PIC version of the MPC Card."
	::= {alarmCardVersionEntry 6 }
	
ipUnityImageVersionObjects OBJECT IDENTIFIER
        ::= { msVersionObjects 6 }

ipUnityCurrentImageVersion OBJECT IDENTIFIER
        ::= { ipUnityImageVersionObjects 1 }

ipUnityCurrentSccImageVersion OBJECT-TYPE
    SYNTAX DisplayString
    MAX-ACCESS read-only
    STATUS current
    DESCRIPTION
        "Current Scc image version."
    ::= { ipUnityCurrentImageVersion 1 }

ipUnityCurrentSccCpImageVersion OBJECT-TYPE
    SYNTAX DisplayString
    MAX-ACCESS read-only
    STATUS current
    DESCRIPTION
        "Current Scc-Cp image version."
    ::= { ipUnityCurrentImageVersion 2 }

ipUnityCurrentOdspImageVersion OBJECT-TYPE
    SYNTAX DisplayString
    MAX-ACCESS read-only
    STATUS current
    DESCRIPTION
        "Current Odsp image version."
    ::= { ipUnityCurrentImageVersion 3 }

ipUnityCurrentDspImageVersion OBJECT-TYPE
    SYNTAX DisplayString
    MAX-ACCESS read-only
    STATUS current
    DESCRIPTION
        "Current Dsp image version."
    ::= { ipUnityCurrentImageVersion 4 }

ipUnityCurrentDspFaxImageVersion OBJECT-TYPE
    SYNTAX DisplayString
    MAX-ACCESS read-only
    STATUS current
    DESCRIPTION
        "Current Dsp Fax image version."
    ::= { ipUnityCurrentImageVersion 5 }

ipUnityCurrentDsp3ImageVersion OBJECT-TYPE
    SYNTAX DisplayString
    MAX-ACCESS read-only
    STATUS current
    DESCRIPTION
        "Current Dsp3 image version."
    ::= { ipUnityCurrentImageVersion 6 }

ipUnityCurrentSpmImageVersion OBJECT-TYPE
    SYNTAX DisplayString
    MAX-ACCESS read-only
    STATUS current
    DESCRIPTION
        "Current Spm image version."
    ::= { ipUnityCurrentImageVersion 7 }

--ipUnityCurrentAsrImageVersion OBJECT-TYPE
--    SYNTAX DisplayString
--    MAX-ACCESS read-only
--    STATUS obsolete
--    DESCRIPTION
--        "Current Asr image version."
--    ::= { ipUnityCurrentImageVersion 8 }

--ipUnityCurrentIcmImageVersion OBJECT-TYPE
--    SYNTAX DisplayString
--    MAX-ACCESS read-only
--    STATUS obsolete
--    DESCRIPTION
--        "Current Icm image version."
--    ::= { ipUnityCurrentImageVersion 9 }

--ipUnityCurrentHttpImageVersion OBJECT-TYPE
--    SYNTAX DisplayString
--    MAX-ACCESS read-only
--    STATUS obsolete
--    DESCRIPTION
--        "Current Http image version."
--    ::= { ipUnityCurrentImageVersion 10 }

ipUnityCurrentVxmlImageVersion OBJECT-TYPE
    SYNTAX DisplayString
    MAX-ACCESS read-only
    STATUS current
    DESCRIPTION
        "Current Vxml image version."
    ::= { ipUnityCurrentImageVersion 11 }

ipUnityCurrentMpc20ImageVersion OBJECT-TYPE
    SYNTAX DisplayString
    MAX-ACCESS read-only
    STATUS current
    DESCRIPTION
        "Current Mpc20 image version."
    ::= { ipUnityCurrentImageVersion 12 }

ipUnityUpgradeImageVersion OBJECT IDENTIFIER
        ::= { ipUnityImageVersionObjects 2 }

ipUnityUpgradeSccImageVersion OBJECT-TYPE
    SYNTAX DisplayString
    MAX-ACCESS read-only
    STATUS current
    DESCRIPTION
        "Upgrade Scc image version."
    ::= { ipUnityUpgradeImageVersion 1 }

ipUnityUpgradeSccCpImageVersion OBJECT-TYPE
    SYNTAX DisplayString
    MAX-ACCESS read-only
    STATUS current
    DESCRIPTION
        "Upgrade Scc-Cp image version."
    ::= { ipUnityUpgradeImageVersion 2 }

ipUnityUpgradeOdspImageVersion OBJECT-TYPE
    SYNTAX DisplayString
    MAX-ACCESS read-only
    STATUS current
    DESCRIPTION
        "Upgrade Odsp image version."
    ::= { ipUnityUpgradeImageVersion 3 }

ipUnityUpgradeDspImageVersion OBJECT-TYPE
    SYNTAX DisplayString
    MAX-ACCESS read-only
    STATUS current
    DESCRIPTION
        "Upgrade Dsp image version."
    ::= { ipUnityUpgradeImageVersion 4 }

ipUnityUpgradeDspFaxImageVersion OBJECT-TYPE
    SYNTAX DisplayString
    MAX-ACCESS read-only
    STATUS current
    DESCRIPTION
        "Upgrade Dsp Fax image version."
    ::= { ipUnityUpgradeImageVersion 5 }

ipUnityUpgradeDsp3ImageVersion OBJECT-TYPE
    SYNTAX DisplayString
    MAX-ACCESS read-only
    STATUS current
    DESCRIPTION
        "Upgrade Dsp3 image version."
    ::= { ipUnityUpgradeImageVersion 6 }

ipUnityUpgradeSpmImageVersion OBJECT-TYPE
    SYNTAX DisplayString
    MAX-ACCESS read-only
    STATUS current
    DESCRIPTION
        "Upgrade Spm image version."
    ::= { ipUnityUpgradeImageVersion 7 }

--ipUnityUpgradeAsrImageVersion OBJECT-TYPE
--    SYNTAX DisplayString
--    MAX-ACCESS read-only
--    STATUS obsolete
--    DESCRIPTION
--        "Upgrade Asr image version."
--    ::= { ipUnityUpgradeImageVersion 8 }

--ipUnityUpgradeIcmImageVersion OBJECT-TYPE
--    SYNTAX DisplayString
--    MAX-ACCESS read-only
--    STATUS obsolete
--    DESCRIPTION
--        "Upgrade Icm image version."
--    ::= { ipUnityUpgradeImageVersion 9 }

--ipUnityUpgradeHttpImageVersion OBJECT-TYPE
--    SYNTAX DisplayString
--    MAX-ACCESS read-only
--    STATUS obsolete
--    DESCRIPTION
--        "Upgrade Http image version."
--    ::= { ipUnityUpgradeImageVersion 10 }

ipUnityUpgradeVxmlImageVersion OBJECT-TYPE
    SYNTAX DisplayString
    MAX-ACCESS read-only
    STATUS current
    DESCRIPTION
        "Upgrade Vxml image version."
    ::= { ipUnityUpgradeImageVersion 11 }

ipUnityUpgradeMpc20ImageVersion OBJECT-TYPE
    SYNTAX DisplayString
    MAX-ACCESS read-only
    STATUS current
    DESCRIPTION
        "Upgrade Mpc20 image version."
    ::= { ipUnityUpgradeImageVersion 12 }

-- Upgrade related objects
imageType OBJECT-TYPE
	SYNTAX INTEGER {
		none (0),
		bulk (2),
		dsp (3),
		odsp (6),
		spm (9),
		vxml (10),
		scc(12),
		mpcTwenty(13)
	}
	MAX-ACCESS read-write
	STATUS current
	DESCRIPTION
		"Type of the image. Gives what kind of image to upgrade.  
		When this object is not set agent returns none(0)."
	::= { msUpgradeObjects 1 }

imagePath OBJECT-TYPE
	SYNTAX DisplayString
	MAX-ACCESS read-write
	STATUS current
	DESCRIPTION
		"file name and path of the image."
	::= { msUpgradeObjects 2 }

imageHostName OBJECT-TYPE
	SYNTAX DisplayString (SIZE(1..64))
	MAX-ACCESS read-write
	STATUS current
	DESCRIPTION
		"Hostname or the IP address on which the image is present. "
	::= { msUpgradeObjects 3 }

imageLogin OBJECT-TYPE
	SYNTAX DisplayString (SIZE(1..32))
	MAX-ACCESS read-write
	STATUS current
	DESCRIPTION
		"Login name for imageHostName. "
	::= { msUpgradeObjects 4 }

imageLoginPassword OBJECT-TYPE
	SYNTAX DisplayString (SIZE(1..32))
	MAX-ACCESS read-write
	STATUS current
	DESCRIPTION
		"Password for the login name imageLogin. "
	::= { msUpgradeObjects 5 }	
	
imageUpgradeCommand OBJECT-TYPE
	SYNTAX INTEGER {
                no-command (0),
		upload (1),
		cancel (2),
		commit (3)
	}
	MAX-ACCESS read-write
	STATUS current
	DESCRIPTION
		"Command for performing image upgrade. Explanation of each command 
		is as follows
		
		upload - Values for all the read-write scalar 
		variables in this group needs to have correct values to 
		perform the image upload operation. Upload can take some time, 
		so the status can be known by querying imageUploadStatus object.
		
		cancel - Once upload is done then user has a choice to cancel it, if
		he would like to use the old image instead of upgrade. This cancels 
		the upgrade for imageType. It is management station's responsibility
		to make sure imageType is set correctly before performing this
		operation.
		
		commit - User is happy with the image and commiting it. This commits
		the upgrade for imageType. It is management station's responsibility
		to make sure imageType is set correctly before performing this operation.
		
		For Get operation this object returns the last command that has been 
		Set."
	::= { msUpgradeObjects 6 }

imageUploadStatus OBJECT-TYPE
	SYNTAX INTEGER {
                no-command (0),
		inprogress (1),
		success (2),
		failed (3)
	}
	MAX-ACCESS read-only
	STATUS current
	DESCRIPTION
		"Status of the current or last upload procedure. If there is no 
		upgrade in progress then it return the status of the last 
		upgrade. "
	::= { msUpgradeObjects 7 }	 		

upgradeCmdFailureReason OBJECT-TYPE
	SYNTAX DisplayString
	MAX-ACCESS read-only
	STATUS current
	DESCRIPTION
		"Failure reason for the last imageUpgradeCommand. This value is useful only
		when imageUploadStatus is failed (3). This string gives the reason for failure."
	::= { msUpgradeObjects 8 }	 		

-- Chassis related objects
ipUnityChassisType OBJECT-TYPE
	SYNTAX INTEGER {
          mereon3000(1),
          mereon6000(0)
        }
	MAX-ACCESS read-only
	STATUS current
	DESCRIPTION
		"Chassis Type."  
	::= { ipUnityMSChassisObjects 1 }

ipUnityChassisSerialNum OBJECT-TYPE
	SYNTAX DisplayString (SIZE(0..24)) 
	MAX-ACCESS read-only
	STATUS current
	DESCRIPTION
		"Chassis Serial Number."
	::= { ipUnityMSChassisObjects 2 }

ipUnityChassisCLEINum OBJECT-TYPE
	SYNTAX DisplayString (SIZE(0..16))
	MAX-ACCESS read-only
	STATUS current
	DESCRIPTION
		"Chassis CLEI Number."
	::= { ipUnityMSChassisObjects 3 }

ipUnityChassisPcbRev OBJECT-TYPE
	SYNTAX DisplayString (SIZE(0..16))
	MAX-ACCESS read-only
	STATUS current
	DESCRIPTION
		"Chassis PCB Rev."
	::= { ipUnityMSChassisObjects 4 }

ipUnityChassisMfgDate OBJECT-TYPE
	SYNTAX DisplayString (SIZE(0..11))
	MAX-ACCESS read-only
	STATUS current
	DESCRIPTION
		"Chassis Manufacturing Date."
	::= { ipUnityMSChassisObjects 5 }	
	
ipUnityBackPlaneType OBJECT-TYPE
    SYNTAX INTEGER {
          mereon3000(1),
          mereon6000(0)
        }	
    MAX-ACCESS read-only
	STATUS current
	DESCRIPTION
		"BackPlane Type."  
	::= { ipUnityMSChassisObjects 6 }

ipUnityBackPlaneSerialNum OBJECT-TYPE
	SYNTAX DisplayString (SIZE(0..24)) 
	MAX-ACCESS read-only
	STATUS current
	DESCRIPTION
		"BackPlane Serial Number."
	::= { ipUnityMSChassisObjects 7 }

ipUnityBackPlaneCLEINum OBJECT-TYPE
	SYNTAX DisplayString (SIZE(0..16))
	MAX-ACCESS read-only
	STATUS current
	DESCRIPTION
		"BackPlane CLEI Number."
	::= { ipUnityMSChassisObjects 8 }

ipUnityBackPlanePcbRev OBJECT-TYPE
	SYNTAX DisplayString (SIZE(0..16))
	MAX-ACCESS read-only
	STATUS current
	DESCRIPTION
		"BackPlane PCB Rev."
	::= { ipUnityMSChassisObjects 9 }

ipUnityBackPlaneMfgDate OBJECT-TYPE
	SYNTAX DisplayString (SIZE(0..11))
	MAX-ACCESS read-only
	STATUS current
	DESCRIPTION
		"BackPlane Manufacturing Date."
	::= { ipUnityMSChassisObjects 10 }	
	
ipUnityFanType OBJECT-TYPE
	SYNTAX INTEGER {
          mereon3000(1),
          mereon6000(0)
        }
	MAX-ACCESS read-only
	STATUS current
	DESCRIPTION
		"Fan Type."  
	::= { ipUnityMSChassisObjects 11}

ipUnityFanSerialNum OBJECT-TYPE
	SYNTAX DisplayString (SIZE(0..24)) 
	MAX-ACCESS read-only
	STATUS current
	DESCRIPTION
		"Fan Serial Number."
	::= { ipUnityMSChassisObjects 12 }

ipUnityFanCLEINum OBJECT-TYPE
	SYNTAX DisplayString (SIZE(0..16))
	MAX-ACCESS read-only
	STATUS current
	DESCRIPTION
		"Fan CLEI Number."
	::= { ipUnityMSChassisObjects 13 }

ipUnityFanPcbRev OBJECT-TYPE
	SYNTAX DisplayString (SIZE(0..16))
	MAX-ACCESS read-only
	STATUS current
	DESCRIPTION
		"Fan PCB Rev."
	::= { ipUnityMSChassisObjects 14 }

ipUnityFanMfgDate OBJECT-TYPE
	SYNTAX DisplayString (SIZE(0..11))
	MAX-ACCESS read-only
	STATUS current
	DESCRIPTION
		"Fan Manufacturing Date."
	::= { ipUnityMSChassisObjects 15 }	
	
ipUnityPemAType OBJECT-TYPE
	SYNTAX INTEGER {
          mereon3000(1),
          mereon6000(0)
        }
	MAX-ACCESS read-only
	STATUS current
	DESCRIPTION
		"PemA Type."  
	::= { ipUnityMSChassisObjects 16 }

ipUnityPemASerialNum OBJECT-TYPE
	SYNTAX DisplayString (SIZE(0..24)) 
	MAX-ACCESS read-only
	STATUS current
	DESCRIPTION
		"PemA Serial Number."
	::= { ipUnityMSChassisObjects 17 }

ipUnityPemACLEINum OBJECT-TYPE
	SYNTAX DisplayString (SIZE(0..16))
	MAX-ACCESS read-only
	STATUS current
	DESCRIPTION
		"PemA CLEI Number."
	::= { ipUnityMSChassisObjects 18 }

ipUnityPemAPcbRev OBJECT-TYPE
	SYNTAX DisplayString (SIZE(0..16))
	MAX-ACCESS read-only
	STATUS current
	DESCRIPTION
		"PemA PCB Rev."
	::= { ipUnityMSChassisObjects 19 }

ipUnityPemAMfgDate OBJECT-TYPE
	SYNTAX DisplayString (SIZE(0..11))
	MAX-ACCESS read-only
	STATUS current
	DESCRIPTION
		"PemA Manufacturing Date."
	::= { ipUnityMSChassisObjects 20 }	

ipUnityPemBType OBJECT-TYPE
	SYNTAX INTEGER {
          mereon3000(1),
          mereon6000(0)
        }
	MAX-ACCESS read-only
	STATUS current
	DESCRIPTION
		"PemB Type."  
	::= { ipUnityMSChassisObjects 21 }

ipUnityPemBSerialNum OBJECT-TYPE
	SYNTAX DisplayString (SIZE(0..24)) 
	MAX-ACCESS read-only
	STATUS current
	DESCRIPTION
		"PemB Serial Number."
	::= { ipUnityMSChassisObjects 22 }

ipUnityPemBCLEINum OBJECT-TYPE
	SYNTAX DisplayString (SIZE(0..16))
	MAX-ACCESS read-only
	STATUS current
	DESCRIPTION
		"PemB CLEI Number."
	::= { ipUnityMSChassisObjects 23 }

ipUnityPemBPcbRev OBJECT-TYPE
	SYNTAX DisplayString (SIZE(0..16))
	MAX-ACCESS read-only
	STATUS current
	DESCRIPTION
		"PemB PCB Rev."
	::= { ipUnityMSChassisObjects 24 }

ipUnityPemBMfgDate OBJECT-TYPE
	SYNTAX DisplayString (SIZE(0..11))
	MAX-ACCESS read-only
	STATUS current
	DESCRIPTION
		"PemB Manufacturing Date."
	::= { ipUnityMSChassisObjects 25 }	

--PEM Status
ipUnityPEMStatus  OBJECT IDENTIFIER ::= { ipUnityMSChassisObjects 26 }

ipUnityPEM48VoltAPowerSupply 	OBJECT-TYPE        
	SYNTAX INTEGER {
		down (0),
		up (1)
	}
        MAX-ACCESS read-only
        STATUS current
        DESCRIPTION		
		"Status of 48 Volts power supply A."
::= { ipUnityPEMStatus 1 }

ipUnityPEM48VoltBPowerSupply 	OBJECT-TYPE        
	SYNTAX INTEGER {
		down (0),
		up (1)
	}
        MAX-ACCESS read-only
        STATUS current
        DESCRIPTION 		
		"Status of 48 Volts power supply B."
::= { ipUnityPEMStatus 2 }

ipUnityPEM5VoltAPowerSupply 	OBJECT-TYPE        
	SYNTAX INTEGER {
		down (0),
		up (1)
	}
        MAX-ACCESS read-only
        STATUS current
        DESCRIPTION 		
		"Status of 5 Volts power supply A."
::= { ipUnityPEMStatus 3 }

ipUnityPEM5VoltBPowerSupply 	OBJECT-TYPE        
	SYNTAX INTEGER {
		down (0),
		up (1)
	}
        MAX-ACCESS read-only
        STATUS current
        DESCRIPTION 		
		"Status of 5 Volts power supply B."
::= { ipUnityPEMStatus 4 }

ipUnityPEMHot5VoltPowerSupply 	OBJECT-TYPE        
	SYNTAX INTEGER {
		down (0),
		up (1)
	}
        MAX-ACCESS read-only
        STATUS current
        DESCRIPTION 		
		"Status of Hot 5 Volts power supply."
::= { ipUnityPEMStatus 5 }

-- The IP Unity Fan Status Table

ipUnityFanStatusTable OBJECT-TYPE
	SYNTAX SEQUENCE OF IpUnityFanStatusEntry
	MAX-ACCESS not-accessible
	STATUS current
	DESCRIPTION
		"A table containing status information of each fan in the Media Server."
	::= { ipUnityMSChassisObjects 27 }

ipUnityFanStatusEntry OBJECT-TYPE
	SYNTAX IpUnityFanStatusEntry
	MAX-ACCESS not-accessible
	STATUS current
	DESCRIPTION
		"An entry in the fan table containing information about the fan status."
    INDEX { ipUnityFanStatusIndex }
	::= { ipUnityFanStatusTable  1 }

IpUnityFanStatusEntry ::= SEQUENCE {
	ipUnityFanStatusIndex				Integer32,
	ipUnityFanStatusVal				INTEGER
}

ipUnityFanStatusIndex OBJECT-TYPE
	SYNTAX Integer32
	MAX-ACCESS not-accessible
	STATUS current
	DESCRIPTION
		"Represents the Fan number."
	::= {ipUnityFanStatusEntry 1 }

ipUnityFanStatusVal OBJECT-TYPE
	SYNTAX INTEGER {
		down (0),
		up (1)
	}
	MAX-ACCESS read-only 
	STATUS current
	DESCRIPTION
		" Represents the Fan status."
	::= {ipUnityFanStatusEntry 2 }

ipUnityOutstandingAlarmTable            OBJECT-TYPE
        SYNTAX SEQUENCE OF IpUnityOutstandingAlarmEntry
	MAX-ACCESS not-accessible
        STATUS current	
        DESCRIPTION
        "The table is used get the outstanding alarm list."
        ::= { ipUnityMaintenanceGroup 9 }

ipUnityOutstandingAlarmEntry  OBJECT-TYPE
        SYNTAX IpUnityOutstandingAlarmEntry
	MAX-ACCESS not-accessible
	STATUS current
	DESCRIPTION
	        "An entry for each outstanding alarm."
        INDEX { ipUnityOutstandingAlarmIndex }
        ::= { ipUnityOutstandingAlarmTable 1 }

IpUnityOutstandingAlarmEntry  ::= SEQUENCE {
        ipUnityOutstandingAlarmIndex    	Integer32,
	ipUnityAlarmName			DisplayString,
        ipUnitySeverityLevel                   	INTEGER,
        ipUnityCardNum                         	Integer32,
        ipUnityBankNum                 		Integer32,
        ipUnityModuleNum             	 	Integer32,
        ipUnityChannelNum             		Integer32,
        ipUnityAlarmTimestamp      	 	DisplayString,
        ipUnitySeqNum                    	Integer32,
        ipUnityAlarmString               	DisplayString,
        ipUnityAlarmAdditionalInfoString        DisplayString,
        ipUnityAlarmAdditionalInfoInt           Integer32	
}

ipUnityOutstandingAlarmIndex    OBJECT-TYPE
	SYNTAX Integer32
	MAX-ACCESS not-accessible
	STATUS current
	DESCRIPTION
		"Outstanding Alarm Index."
	::= { ipUnityOutstandingAlarmEntry 1 }


ipUnityAlarmName OBJECT-TYPE
  	SYNTAX DisplayString
	MAX-ACCESS read-only
	STATUS current
	DESCRIPTION
		"The Alarm Name."
	::= { ipUnityOutstandingAlarmEntry 2 }
	
ipUnitySeverityLevel OBJECT-TYPE
	SYNTAX      INTEGER {
	      clear (1),
	      informational (2),
	      warning (3),
	      minor (4),
	      major (5),
	      critical (6)
	}
	MAX-ACCESS read-only
	STATUS current
	DESCRIPTION
		"Trap severity level."
	::= { ipUnityOutstandingAlarmEntry 3 }

ipUnityCardNum  OBJECT-TYPE
	SYNTAX Integer32
	MAX-ACCESS read-only
	STATUS current
	DESCRIPTION
	    "Card Number."
	::= { ipUnityOutstandingAlarmEntry 4 }

ipUnityBankNum OBJECT-TYPE
        SYNTAX Integer32
	MAX-ACCESS read-only
	STATUS current
	DESCRIPTION
	    "Bank Number."
	::= { ipUnityOutstandingAlarmEntry 5 }

ipUnityModuleNum OBJECT-TYPE
        SYNTAX Integer32
	MAX-ACCESS read-only
	STATUS current
	DESCRIPTION
	    "Module Number."
	::= { ipUnityOutstandingAlarmEntry 6 }

ipUnityChannelNum OBJECT-TYPE
        SYNTAX Integer32
	MAX-ACCESS read-only
	STATUS current
	DESCRIPTION
	     "Channel Number."
	::= { ipUnityOutstandingAlarmEntry 7 }

ipUnityAlarmTimestamp    OBJECT-TYPE
  	SYNTAX DisplayString
        MAX-ACCESS read-only
	STATUS current
	DESCRIPTION
	     "The time of occurance of the trap."
	::= { ipUnityOutstandingAlarmEntry 8 }

ipUnitySeqNum   OBJECT-TYPE
        SYNTAX Integer32
	MAX-ACCESS read-only
	STATUS current
	DESCRIPTION
	     "The sequence number associated with the alarm."
	::= { ipUnityOutstandingAlarmEntry 9 }

ipUnityAlarmString OBJECT-TYPE
        SYNTAX DisplayString
	MAX-ACCESS read-only
	STATUS current
	DESCRIPTION
	    "The Alarm String."
	::= { ipUnityOutstandingAlarmEntry 10 }

ipUnityAlarmAdditionalInfoString OBJECT-TYPE
        SYNTAX DisplayString
	MAX-ACCESS read-only
	STATUS current
	DESCRIPTION
	     "This object gives the additional info string based on the trap and can hold any one of the following strings,
	      ipUnitySccTaskName OR ipUnitySccFileSystemName OR pUnitySccLogFileName OR ipUnityOdspTaskName
	      OR ipUnityOdspLogFileName OR ipUnityTaskName OR ipUnityLogFileName. This object will report null in the absence of 
	      additional string value. "
	::= { ipUnityOutstandingAlarmEntry 11 }

ipUnityAlarmAdditionalInfoInt OBJECT-TYPE
        SYNTAX Integer32
	MAX-ACCESS read-only
	STATUS current
	DESCRIPTION
	    "This object gives the additional info integer value based on the trap and can hold values for any one of the 
	     following additional info. ipUnityFanNumber OR ipUnityPowerSupplyType OR ipUnitySystemTemperature
	     This object will report .-1. in the absence of any additional info integer value."
	::= { ipUnityOutstandingAlarmEntry 12 }

-- IP Unity proprietary statistics objects

ipUnityCallStatistics       OBJECT IDENTIFIER ::= { ipUnityStatistics 1 }
ipUnityMgcpStatistics		OBJECT IDENTIFIER ::= { ipUnityStatistics 2 }
ipUnityResourceStatistics 	OBJECT IDENTIFIER ::= { ipUnityStatistics 3 }
ipUnitySystemStatistics		OBJECT IDENTIFIER ::= { ipUnityStatistics 4 }

-- Call statistics

ipUnityNumCallSetupAttempts	OBJECT-TYPE
        SYNTAX Counter32
        MAX-ACCESS read-only
        STATUS current
        DESCRIPTION
                "The number of Call Setup attempts made."
        ::= { ipUnityCallStatistics 1 }

ipUnityNumCallTearDownAttempts	OBJECT-TYPE
        SYNTAX Counter32
        MAX-ACCESS read-only
        STATUS current
        DESCRIPTION
                "The number of Call TearDown attempts made."
        ::= { ipUnityCallStatistics 2 }

ipUnityNumCallSetupFailures	OBJECT-TYPE
        SYNTAX Counter32
        MAX-ACCESS read-only
        STATUS current
        DESCRIPTION
                "The number of Call Setup attempts which failed."
        ::= { ipUnityCallStatistics 3 }

ipUnityNumRscAllocFailures	OBJECT-TYPE
        SYNTAX Counter32
        MAX-ACCESS read-only
        STATUS current
        DESCRIPTION
                "The number of Resource Allocation attempts which failed."
        ::= { ipUnityCallStatistics 4 }

ipUnityNumChanOpenFailures	OBJECT-TYPE
        SYNTAX Counter32
        MAX-ACCESS read-only
        STATUS current
        DESCRIPTION
                "The number of Channel Open attempts which failed."
        ::= { ipUnityCallStatistics 5 }

ipUnityNumATMConnFailures	OBJECT-TYPE
        SYNTAX Counter32
        MAX-ACCESS read-only
        STATUS current
        DESCRIPTION
                "The number of ATM Connection attempts which failed."
        ::= { ipUnityCallStatistics 6 }

ipUnityNumCallTearDownFailures	OBJECT-TYPE
        SYNTAX Counter32
        MAX-ACCESS read-only
        STATUS current
        DESCRIPTION
                "The number of Call TearDown attempts which failed."
        ::= { ipUnityCallStatistics 7 }

ipUnityNumRscFreeFailures	OBJECT-TYPE
        SYNTAX Counter32
        MAX-ACCESS read-only
        STATUS current
        DESCRIPTION
                "The number of Resource Freeing attempts which failed."
        ::= { ipUnityCallStatistics 8 }

ipUnityNumChanCloseFailures	OBJECT-TYPE
        SYNTAX Counter32
        MAX-ACCESS read-only
        STATUS current
        DESCRIPTION
                "The number of Channel Close attempts which failed."
        ::= { ipUnityCallStatistics 9 }

ipUnityNumATMDiscFailures	OBJECT-TYPE
        SYNTAX Counter32
        MAX-ACCESS read-only
        STATUS current
        DESCRIPTION
                "The number of ATM Disconnect attempts which failed."
        ::= { ipUnityCallStatistics 10 }

ipUnityNumServiceRequestAttempts	OBJECT-TYPE
        SYNTAX Counter32
        MAX-ACCESS read-only
        STATUS current
        DESCRIPTION
                "The number of service requests attempts made."
        ::= { ipUnityCallStatistics 11 }

ipUnityNumServiceRequestFailures	OBJECT-TYPE
        SYNTAX Counter32
        MAX-ACCESS read-only
        STATUS current
        DESCRIPTION
                "The number of service requests attempts which failed."
        ::= { ipUnityCallStatistics 12 }

ipUnityNumAsrRequested		OBJECT-TYPE
        SYNTAX Counter32
        MAX-ACCESS read-only
        STATUS current
        DESCRIPTION
                "The number of ASR requests."
        ::= { ipUnityCallStatistics 13 }

ipUnityNumAsrAllocationFailure	OBJECT-TYPE
        SYNTAX Counter32
        MAX-ACCESS read-only
        STATUS current
        DESCRIPTION
                "The number of ASR allocation failures."
        ::= { ipUnityCallStatistics 14 }

ipUnityNumAsrATMConnectionFailure	OBJECT-TYPE
        SYNTAX Counter32
        MAX-ACCESS read-only
        STATUS current
        DESCRIPTION
                "The number of ASR ATM connection failures."
        ::= { ipUnityCallStatistics 15 }

ipUnityNumAsrATMDisconnectFailure	OBJECT-TYPE
        SYNTAX Counter32
        MAX-ACCESS read-only
        STATUS current
        DESCRIPTION
                "The number of ASR ATM disconnect failures."
        ::= { ipUnityCallStatistics 16 }

ipUnityNumAsrFreeFailure	OBJECT-TYPE
        SYNTAX Counter32
        MAX-ACCESS read-only
        STATUS current
        DESCRIPTION
                "The number of ASR free failures."
        ::= { ipUnityCallStatistics 17 }

-- MGCP statistics

mgcpCrcxReceived 	OBJECT-TYPE 
        SYNTAX Counter32
        MAX-ACCESS read-only
        STATUS current
        DESCRIPTION
                "The number of CreateConnection (CRCX) messages received by the Media Server."
::= { ipUnityMgcpStatistics 1 }

mgcpCrcxResponded OBJECT-TYPE        
	SYNTAX Counter32
        MAX-ACCESS read-only
        STATUS current
        DESCRIPTION
                "The number of CreateConnection (CRCX) messages to which the Media Server responded."
::= { ipUnityMgcpStatistics 2 }

mgcpCrcxRespondedErr OBJECT-TYPE        
	SYNTAX Counter32
        MAX-ACCESS read-only
        STATUS current
        DESCRIPTION
                "The number of CreateConnection (CRCX) messages to which the Media Server responded 
		indicating the error(s)."
::= { ipUnityMgcpStatistics 3 }

mgcpCrcxSent OBJECT-TYPE        
	SYNTAX Counter32
        MAX-ACCESS read-only
        STATUS current
        DESCRIPTION
                "The number of CreateConnection (CRCX) messages sent by the Media Server."

::= { ipUnityMgcpStatistics 4 }

mgcpMdcxReceived OBJECT-TYPE        
	SYNTAX Counter32
        MAX-ACCESS read-only
        STATUS current
        DESCRIPTION
                "The number of ModifyConnection (MDCX) messages 
received by the Media Server."
::= { ipUnityMgcpStatistics 5 }

mgcpMdcxResponded OBJECT-TYPE        
	SYNTAX Counter32
        MAX-ACCESS read-only
        STATUS current
        DESCRIPTION
                "The number of ModifyConnection (MDCX)
messages to which the Media Server responded."
::= { ipUnityMgcpStatistics 6 }

mgcpMdcxRespondedErr OBJECT-TYPE        
		SYNTAX Counter32
        MAX-ACCESS read-only
        STATUS current
        DESCRIPTION
                "The number of ModifyConnection (MDCX) messages to which the Media Server responded 
		indicating the error(s)."
::= { ipUnityMgcpStatistics 7 }

mgcpMdcxSent OBJECT-TYPE        
	SYNTAX Counter32
        MAX-ACCESS read-only
        STATUS current
        DESCRIPTION
                "The number of ModifyConnection (MDCX) messages sent by the Media Server."
::= { ipUnityMgcpStatistics 8 }

mgcpDlcxReceived OBJECT-TYPE        
	SYNTAX Counter32
        MAX-ACCESS read-only
        STATUS current
        DESCRIPTION
                "The number of DeleteConnection (DLCX) messages received by the Media Server."
::= { ipUnityMgcpStatistics 9 }

mgcpDlcxResponded OBJECT-TYPE        
	SYNTAX Counter32
        MAX-ACCESS read-only
        STATUS current
        DESCRIPTION
                "The number of DeleteConnection (DLCX) messages
to which the Media Server responded."
::= { ipUnityMgcpStatistics 10 }

mgcpDlcxRespondedErr OBJECT-TYPE        
	SYNTAX Counter32
        MAX-ACCESS read-only
        STATUS current
        DESCRIPTION
                "The number of DeleteConnection (DLCX) messages to which the Media Server responded 
		indicating the error(s)."
::= { ipUnityMgcpStatistics 11 }

mgcpDlcxSent OBJECT-TYPE        
	SYNTAX Counter32
        MAX-ACCESS read-only
        STATUS current
        DESCRIPTION
                "The number of DeleteConnection (DLCX) messages sent by the Media Server."
::= { ipUnityMgcpStatistics 12 }

mgcpRqntReceived OBJECT-TYPE        
	SYNTAX Counter32
        MAX-ACCESS read-only
        STATUS current
        DESCRIPTION
                "The number of NotificationRequest (RQNT) messages received by the Media Server."
::= { ipUnityMgcpStatistics 13 }

mgcpRqntResponded OBJECT-TYPE        
	SYNTAX Counter32
        MAX-ACCESS read-only
        STATUS current
        DESCRIPTION
                "The number of NotificationRequest (RQNT) messages to which the Media Server responded."
::= { ipUnityMgcpStatistics 14 }

mgcpRqntRespondedErr OBJECT-TYPE        
	SYNTAX Counter32
        MAX-ACCESS read-only
        STATUS current
        DESCRIPTION
                "The number of NotificationRequest (RQNT) messages to which the Media Server responded 
		indicating the error(s)."
::= { ipUnityMgcpStatistics 15 }

mgcpRqntSent OBJECT-TYPE        
	SYNTAX Counter32
        MAX-ACCESS read-only
        STATUS current
        DESCRIPTION
                "The number of NotificationRequest (RQNT) messages sent by the Media Server."
::= { ipUnityMgcpStatistics 16 }

mgcpNtfyReceived OBJECT-TYPE        
	SYNTAX Counter32
        MAX-ACCESS read-only
        STATUS current
        DESCRIPTION
                "The number of Notify (NTFY) messages received by the Media Server."
::= { ipUnityMgcpStatistics 17 }

mgcpNtfyResponded OBJECT-TYPE        
	SYNTAX Counter32
        MAX-ACCESS read-only
        STATUS current
        DESCRIPTION
                "The number of Notify (NTFY) messages to which the Media Server responded."
::= { ipUnityMgcpStatistics 18 }

mgcpNtfyRespondedErr OBJECT-TYPE        
	SYNTAX Counter32
        MAX-ACCESS read-only
        STATUS current
        DESCRIPTION
                "The number of Notify (NTFY) messages to which the Media Server responded 
		indicating the error(s)."
::= { ipUnityMgcpStatistics 19 }

mgcpNtfySent OBJECT-TYPE        
	SYNTAX Counter32
        MAX-ACCESS read-only
        STATUS current
        DESCRIPTION
                "The number of Notify (NTFY) messages sent by the Media Server."
::= { ipUnityMgcpStatistics 20 }

mgcpAuepReceived OBJECT-TYPE        
	SYNTAX Counter32
        MAX-ACCESS read-only
        STATUS current
        DESCRIPTION
                "The number of AuditEndpoint (AUEP) messages received by the Media Server."
::= { ipUnityMgcpStatistics 21 }

mgcpAuepResponded OBJECT-TYPE        
	SYNTAX Counter32
        MAX-ACCESS read-only
        STATUS current
        DESCRIPTION
                "The number of AuditEndpoint (AUEP) messages to which the Media Server responded."
::= { ipUnityMgcpStatistics 22 }

mgcpAuepRespondedErr OBJECT-TYPE        
	SYNTAX Counter32
        MAX-ACCESS read-only
        STATUS current
        DESCRIPTION
                "The number of AuditEndpoint (AUEP) messages to which the Media Server responded 
		indicating the error(s)."
::= { ipUnityMgcpStatistics 23 }

mgcpAuepSent OBJECT-TYPE        
	SYNTAX Counter32
        MAX-ACCESS read-only
        STATUS current
        DESCRIPTION
                "The number of AuditEndpoint (AUEP) messages sent by the Media Server."
::= { ipUnityMgcpStatistics 24 }

mgcpSuccessRecvs 	OBJECT-TYPE        
        SYNTAX Counter32
        MAX-ACCESS read-only
        STATUS current
        DESCRIPTION
                "The number of MGCP messages successfully received ."
::= { ipUnityMgcpStatistics 25 }

mgcpSuccessSends 	OBJECT-TYPE        
        SYNTAX Counter32
        MAX-ACCESS read-only
        STATUS current
        DESCRIPTION
                "The number of MGCP messages successfully sent." 
::= { ipUnityMgcpStatistics 26 }

mgcpInBadVersions 	OBJECT-TYPE        
        SYNTAX Counter32
        MAX-ACCESS read-only
        STATUS current
        DESCRIPTION
        	"The total number of incoming messages which were delivered to the protocol entity 
		and were for an unsupported protocol version."
::= { ipUnityMgcpStatistics 27 }

mgcpUnRecognizedPackets  OBJECT-TYPE
    SYNTAX      Counter32
    MAX-ACCESS  read-only
    STATUS      current
    DESCRIPTION
        	" This refers to the count of unrecognized packets since reset.
        "
    ::= { ipUnityMgcpStatistics 28 }

mgcpInvalidParams 	OBJECT-TYPE        
        SYNTAX Counter32
        MAX-ACCESS read-only
        STATUS current
        DESCRIPTION
                "The number of MGCP requests received with invalid parameters (e.g. 
		connection id, call id, invalid SDP)." 
::= { ipUnityMgcpStatistics 29 }

mgcpRetransmissionsDueToTimeouts 	OBJECT-TYPE        
        SYNTAX Counter32
        MAX-ACCESS read-only
        STATUS current
        DESCRIPTION
                "The number of MGCP requests that were retransmitted due to timeouts."
::= { ipUnityMgcpStatistics 30 }

mgcpOverloadProtectionCounter 	OBJECT-TYPE        
        SYNTAX Counter32
        MAX-ACCESS read-only
        STATUS current
        DESCRIPTION
                "The number of times that MGCP overload occured."
::= { ipUnityMgcpStatistics 31 }

ipUnityMgcpNumOfCallsXceededPktLossThreshold            OBJECT-TYPE
        SYNTAX Counter32
        MAX-ACCESS read-only
        STATUS current
        DESCRIPTION
                "Number of calls that exceed provisioned QoS threshold for latency"
        ::= { ipUnityMgcpStatistics 32 }

ipUnityMgcpNumOfCallsXceededJitterThreshold            OBJECT-TYPE
        SYNTAX Counter32
        MAX-ACCESS read-only
        STATUS current
        DESCRIPTION
                "Number of calls that exceed provisioned QoS threshold for packet loss."
        ::= { ipUnityMgcpStatistics 33 }

ipUnityNumMgcpNumOfCallsXceededAvgLatencyThreshold            OBJECT-TYPE
        SYNTAX Counter32
        MAX-ACCESS read-only
        STATUS current
        DESCRIPTION
                "Number of calls that exceed provisioned QoS threshold for jitter."
        ::= { ipUnityMgcpStatistics 34 }

-- Resource statistics

ipUnitySystemLevelResourceStatistics   OBJECT IDENTIFIER ::= { ipUnityResourceStatistics 1 }

ipUnityModulesAvailableInSystem 	OBJECT-TYPE        
        SYNTAX Integer32	
        MAX-ACCESS read-only
        STATUS current
        DESCRIPTION		
		"Total number of modules (e.g. DSP resources) available in the system."
::= { ipUnitySystemLevelResourceStatistics 1 }

ipUnityModulesOOSInSystem 	OBJECT-TYPE        
        SYNTAX Integer32
        MAX-ACCESS read-only
        STATUS current
        DESCRIPTION 		
		"Total number of out-of-service modules (e.g. DSP resources) in the system." 
::= { ipUnitySystemLevelResourceStatistics 2 }

ipUnityModulesISInSystem 	OBJECT-TYPE        
        SYNTAX Integer32
        MAX-ACCESS read-only
        STATUS current
        DESCRIPTION 		
		"Total number of in-service modules (e.g. DSP resources) in the system."
::= { ipUnitySystemLevelResourceStatistics 3 }

ipUnityConfiguredConfChannelsInSystem 	OBJECT-TYPE        
        SYNTAX Integer32
        MAX-ACCESS read-only
        STATUS current
        DESCRIPTION 		" Total number of configured conference channels in the system."
::= { ipUnitySystemLevelResourceStatistics 4 }

ipUnityAvailableConfChannelsInSystem 	OBJECT-TYPE        
        SYNTAX Integer32
        MAX-ACCESS read-only
        STATUS current
        DESCRIPTION 		" Total number of available conference channels in the system."
::= { ipUnitySystemLevelResourceStatistics 5 }

ipUnityOOSConfChannelsInSystem    OBJECT-TYPE
        SYNTAX Integer32
        MAX-ACCESS read-only
        STATUS current
        DESCRIPTION 		" Total number of out-of-service conference channels in the system."
::= { ipUnitySystemLevelResourceStatistics 6 }

ipUnityISConfChannelsInSystem 	OBJECT-TYPE        
        SYNTAX Integer32
        MAX-ACCESS read-only
        STATUS current
        DESCRIPTION 		" Total number of in-service conference channels in the system."
::= { ipUnitySystemLevelResourceStatistics 7 }

ipUnityActiveConfChannelsInSystem    OBJECT-TYPE
        SYNTAX Integer32
        MAX-ACCESS read-only
        STATUS current
        DESCRIPTION 		" Total number of active conference channels in the system."
::= { ipUnitySystemLevelResourceStatistics 8 }

ipUnityConfiguredIvrChannelsInSystem	OBJECT-TYPE        
        SYNTAX Integer32
        MAX-ACCESS read-only
        STATUS current
        DESCRIPTION 		" Total number of configured IVR channels in the system."
::= { ipUnitySystemLevelResourceStatistics 9 }

ipUnityAvailableIvrChannelsInSystem 	OBJECT-TYPE        
        SYNTAX Integer32
        MAX-ACCESS read-only
        STATUS current
        DESCRIPTION 		" Total number of available IVR channels in the system."
::= { ipUnitySystemLevelResourceStatistics 10 }

ipUnityOOSIvrChannelsInSystem 	OBJECT-TYPE        
        SYNTAX Integer32
        MAX-ACCESS read-only
        STATUS current
        DESCRIPTION 		" Total number of out-of-service IVR channels in the system."
::= { ipUnitySystemLevelResourceStatistics 11 }

ipUnityISIvrChannelsInSystem 	OBJECT-TYPE        
        SYNTAX Integer32
        MAX-ACCESS read-only
        STATUS current
        DESCRIPTION 		" Total number of in-service IVR channels in the system."
::= { ipUnitySystemLevelResourceStatistics 12 }

ipUnityActiveIvrChannelsInSystem    OBJECT-TYPE
        SYNTAX Integer32
        MAX-ACCESS read-only
        STATUS current
        DESCRIPTION 		" Total number of active IVR channels in the system."
::= { ipUnitySystemLevelResourceStatistics 13 }

ipUnityConfiguredAhConfChannelsInSystem	OBJECT-TYPE        
        SYNTAX Integer32
        MAX-ACCESS read-only
        STATUS current
        DESCRIPTION 		" Total number of configured adhoc conference channels in the system."
::= { ipUnitySystemLevelResourceStatistics 14 }

ipUnityAvailableAhConfChannelsInSystem 	OBJECT-TYPE        
        SYNTAX Integer32
        MAX-ACCESS read-only
        STATUS current
        DESCRIPTION 		" Total number of available adhoc conference channels in the system."
::= { ipUnitySystemLevelResourceStatistics 15 }

ipUnityOOSAhConfChannelsInSystem 	OBJECT-TYPE        
        SYNTAX Integer32
        MAX-ACCESS read-only
        STATUS current
        DESCRIPTION 		" Total number of out-of-service adhoc conference channels in the system."
::= { ipUnitySystemLevelResourceStatistics 16 }

ipUnityISAhConfChannelsInSystem 	OBJECT-TYPE        
        SYNTAX Integer32
        MAX-ACCESS read-only
        STATUS current
        DESCRIPTION 		" Total number of in-service adhoc conference channels in the system."
::= { ipUnitySystemLevelResourceStatistics 17 }

ipUnityActiveAhConfChannelsInSystem    OBJECT-TYPE
        SYNTAX Integer32
        MAX-ACCESS read-only
        STATUS current
        DESCRIPTION 		" Total number of active adhoc conference channels in the system."
::= { ipUnitySystemLevelResourceStatistics 18 }

ipUnityConfiguredAsrChannelsInSystem	OBJECT-TYPE        
        SYNTAX Integer32
        MAX-ACCESS read-only
        STATUS current
        DESCRIPTION 		" Total number of configured ASR channels in the system."
::= { ipUnitySystemLevelResourceStatistics 19 }

ipUnityAvailableAsrChannelsInSystem 	OBJECT-TYPE        
        SYNTAX Integer32
        MAX-ACCESS read-only
        STATUS current
        DESCRIPTION 		" Total number of available ASR channels in the system."
::= { ipUnitySystemLevelResourceStatistics 20 }

ipUnityOOSAsrChannelsInSystem 	OBJECT-TYPE        
        SYNTAX Integer32
        MAX-ACCESS read-only
        STATUS current
        DESCRIPTION 		" Total number of out-of-service ASR channels in the system."
::= { ipUnitySystemLevelResourceStatistics 21 }

ipUnityISAsrChannelsInSystem 	OBJECT-TYPE        
        SYNTAX Integer32
        MAX-ACCESS read-only
        STATUS current
        DESCRIPTION 		" Total number of in-service ASR channels in the system."
::= { ipUnitySystemLevelResourceStatistics 22 }

ipUnityActiveAsrChannelsInSystem    OBJECT-TYPE
        SYNTAX Integer32
        MAX-ACCESS read-only
        STATUS current
        DESCRIPTION 		" Total number of active ASR channels in the system."
::= { ipUnitySystemLevelResourceStatistics 23 }

ipUnityConfiguredVxmlChannelsInSystem	OBJECT-TYPE        
        SYNTAX Integer32
        MAX-ACCESS read-only
        STATUS current
        DESCRIPTION 		" Total number of configured Vxml channels in the system."
::= { ipUnitySystemLevelResourceStatistics 24 }

ipUnityAvailableVxmlChannelsInSystem 	OBJECT-TYPE        
        SYNTAX Integer32
        MAX-ACCESS read-only
        STATUS current
        DESCRIPTION 		" Total number of available Vxml channels in the system."
::= { ipUnitySystemLevelResourceStatistics 25 }

ipUnityOOSVxmlChannelsInSystem 	OBJECT-TYPE        
        SYNTAX Integer32
        MAX-ACCESS read-only
        STATUS current
        DESCRIPTION 		" Total number of out-of-service Vxml channels in the system."
::= { ipUnitySystemLevelResourceStatistics 26 }

ipUnityISVxmlChannelsInSystem 	OBJECT-TYPE        
        SYNTAX Integer32
        MAX-ACCESS read-only
        STATUS current
        DESCRIPTION 		" Total number of in-service Vxml channels in the system."
::= { ipUnitySystemLevelResourceStatistics 27 }

ipUnityActiveVxmlChannelsInSystem    OBJECT-TYPE
        SYNTAX Integer32
        MAX-ACCESS read-only
        STATUS current
        DESCRIPTION 		" Total number of active Vxml channels in the system."
::= { ipUnitySystemLevelResourceStatistics 28 }

ipUnityConfiguredHttpChannelsInSystem	OBJECT-TYPE        
        SYNTAX Integer32
        MAX-ACCESS read-only
        STATUS current
        DESCRIPTION 		" Total number of configured HTTP channels in the system."
::= { ipUnitySystemLevelResourceStatistics 29 }

ipUnityAvailableHttpChannelsInSystem 	OBJECT-TYPE        
        SYNTAX Integer32
        MAX-ACCESS read-only
        STATUS current
        DESCRIPTION 		" Total number of available HTTP channels in the system."
::= { ipUnitySystemLevelResourceStatistics 30 }

ipUnityOOSHttpChannelsInSystem 	OBJECT-TYPE        
        SYNTAX Integer32
        MAX-ACCESS read-only
        STATUS current
        DESCRIPTION 		" Total number of out-of-service HTTP channels in the system."
::= { ipUnitySystemLevelResourceStatistics 31 }

ipUnityISHttpChannelsInSystem 	OBJECT-TYPE        
        SYNTAX Integer32
        MAX-ACCESS read-only
        STATUS current
        DESCRIPTION 		" Total number of in-service HTTP channels in the system."
::= { ipUnitySystemLevelResourceStatistics 32 }

ipUnityActiveHttpChannelsInSystem    OBJECT-TYPE
        SYNTAX Integer32
        MAX-ACCESS read-only
        STATUS current
        DESCRIPTION 		" Total number of active HTTP channels in the system."
::= { ipUnitySystemLevelResourceStatistics 33 }

-- tables of resource statistics

ipUnityCardLevelResourceStatisticsTable   OBJECT-TYPE
        SYNTAX SEQUENCE OF IpUnityCardLevelResourceStatisticsEntry
        MAX-ACCESS not-accessible
        STATUS current
        DESCRIPTION " A table containing resource numbers per card in the Media Server."
 ::= { ipUnityResourceStatistics 2 }

ipUnityCardLevelResourceStatisticsEntry  OBJECT-TYPE
    SYNTAX IpUnityCardLevelResourceStatisticsEntry
    MAX-ACCESS not-accessible
    STATUS current
    DESCRIPTION
        "An entry in the card level resource statistics table."
    INDEX      { ipUnityCardIndex }
    ::= { ipUnityCardLevelResourceStatisticsTable  1 }


IpUnityCardLevelResourceStatisticsEntry ::= SEQUENCE {
		ipUnityModulesAvailableInCard          Integer32,
		ipUnityModulesOOSInCard                Integer32,
		ipUnityModulesISInCard                 Integer32,
		ipUnityConfChannelsAvailableInCard     Integer32,
		ipUnityConfChannelsOOSInCard           Integer32,
		ipUnityConfChannelsISInCard            Integer32,
		ipUnityConfChannelsActiveInCard        Integer32,
		ipUnityIvrChannelsAvailableInCard      Integer32,
		ipUnityIvrChannelsOOSInCard            Integer32,
		ipUnityIvrChannelsISInCard             Integer32,
		ipUnityIvrChannelsActiveInCard         Integer32,
		ipUnityAhConfChannelsAvailableInCard   Integer32,
		ipUnityAhConfChannelsOOSInCard         Integer32,
		ipUnityAhConfChannelsISInCard          Integer32,
		ipUnityAhConfChannelsActiveInCard      Integer32,
		ipUnityAsrChannelsAvailableInCard      Integer32,
		ipUnityAsrChannelsOOSInCard            Integer32,
		ipUnityAsrChannelsISInCard             Integer32,
		ipUnityAsrChannelsActiveInCard         Integer32,
		ipUnityVxmlChannelsAvailableInCard     Integer32,
		ipUnityVxmlChannelsOOSInCard           Integer32,
		ipUnityVxmlChannelsISInCard            Integer32,
		ipUnityVxmlChannelsActiveInCard        Integer32,
		ipUnityHttpChannelsAvailableInCard     Integer32,
		ipUnityHttpChannelsOOSInCard           Integer32,
		ipUnityHttpChannelsISInCard            Integer32,
		ipUnityHttpChannelsActiveInCard        Integer32
}

ipUnityModulesAvailableInCard 	OBJECT-TYPE        
        SYNTAX Integer32
        MAX-ACCESS read-only
        STATUS current
        DESCRIPTION		"Total number of modules (e.g. DSP resources) available in a particular card."
::= { ipUnityCardLevelResourceStatisticsEntry 1 }

ipUnityModulesOOSInCard 	OBJECT-TYPE        
        SYNTAX Integer32
        MAX-ACCESS read-only
        STATUS current
        DESCRIPTION 		"Total number of out-of-service modules (e.g. DSP resources) in a particular card." 
::= { ipUnityCardLevelResourceStatisticsEntry 2 }

ipUnityModulesISInCard 	OBJECT-TYPE        
        SYNTAX Integer32
        MAX-ACCESS read-only
        STATUS current
        DESCRIPTION 		"Total number of in-service modules (e.g. DSP resources) in a particular card."
::= { ipUnityCardLevelResourceStatisticsEntry 3 }

ipUnityConfChannelsAvailableInCard 	OBJECT-TYPE        
        SYNTAX Integer32
        MAX-ACCESS read-only
        STATUS current
        DESCRIPTION		"Total number of available conference channels in a particular card. "
::= { ipUnityCardLevelResourceStatisticsEntry 4 }

ipUnityConfChannelsOOSInCard 	OBJECT-TYPE        
        SYNTAX Integer32
        MAX-ACCESS read-only
        STATUS current
        DESCRIPTION		"Total number of Out-Of-Service conference channels in a particular card. "
::= { ipUnityCardLevelResourceStatisticsEntry 5 }

ipUnityConfChannelsISInCard 	OBJECT-TYPE        
        SYNTAX Integer32
        MAX-ACCESS read-only
        STATUS current
        DESCRIPTION	"Total number of In-Service conference channels in a particular card."
::= { ipUnityCardLevelResourceStatisticsEntry 6 }

ipUnityConfChannelsActiveInCard 	OBJECT-TYPE        
        SYNTAX Integer32
        MAX-ACCESS read-only
        STATUS current
        DESCRIPTION		"Total number of active conference channels in a particular card. "
::= { ipUnityCardLevelResourceStatisticsEntry 7 }

ipUnityIvrChannelsAvailableInCard 	OBJECT-TYPE        
        SYNTAX Integer32
        MAX-ACCESS read-only
        STATUS current
        DESCRIPTION		"Total number of available IVR channels in a particular card."
::= { ipUnityCardLevelResourceStatisticsEntry 8 }

ipUnityIvrChannelsOOSInCard 	OBJECT-TYPE        
        SYNTAX Integer32
        MAX-ACCESS read-only
        STATUS current
        DESCRIPTION		"Total number of Out-Of-Service IVR channels in a particular card "
::= { ipUnityCardLevelResourceStatisticsEntry 9 }

ipUnityIvrChannelsISInCard 	OBJECT-TYPE        
        SYNTAX Integer32
        MAX-ACCESS read-only
        STATUS current
        DESCRIPTION	"Total number of In-Service IVR channels in a particular card ."
::= { ipUnityCardLevelResourceStatisticsEntry 10 }

ipUnityIvrChannelsActiveInCard 	OBJECT-TYPE        
        SYNTAX Integer32
        MAX-ACCESS read-only
        STATUS current
        DESCRIPTION		"Total number of active IVR channels in a particular card "
::= { ipUnityCardLevelResourceStatisticsEntry 11 }


ipUnityAhConfChannelsAvailableInCard 	OBJECT-TYPE        
        SYNTAX Integer32
        MAX-ACCESS read-only
        STATUS current
        DESCRIPTION		"Total number of available adhoc conference channels in a particular card. "
::= { ipUnityCardLevelResourceStatisticsEntry 12 }

ipUnityAhConfChannelsOOSInCard 	OBJECT-TYPE        
        SYNTAX Integer32
        MAX-ACCESS read-only
        STATUS current
        DESCRIPTION		"Total number of Out-Of-Service adhoc conference channels in a particular card. "
::= { ipUnityCardLevelResourceStatisticsEntry 13 }

ipUnityAhConfChannelsISInCard 	OBJECT-TYPE        
        SYNTAX Integer32
        MAX-ACCESS read-only
        STATUS current
        DESCRIPTION	"Total number of In-Service adhoc conference channels in a particular card."
::= { ipUnityCardLevelResourceStatisticsEntry 14 }

ipUnityAhConfChannelsActiveInCard 	OBJECT-TYPE        
        SYNTAX Integer32
        MAX-ACCESS read-only
        STATUS current
        DESCRIPTION		"Total number of active adhoc conference channels in a particular card. "
::= { ipUnityCardLevelResourceStatisticsEntry 15 }

ipUnityAsrChannelsAvailableInCard 	OBJECT-TYPE        
        SYNTAX Integer32
        MAX-ACCESS read-only
        STATUS current
        DESCRIPTION		"Total number of available ASR channels in a particular card. "
::= { ipUnityCardLevelResourceStatisticsEntry 16 }

ipUnityAsrChannelsOOSInCard 	OBJECT-TYPE        
        SYNTAX Integer32
        MAX-ACCESS read-only
        STATUS current
        DESCRIPTION		"Total number of Out-Of-Service ASR channels in a particular card. "
::= { ipUnityCardLevelResourceStatisticsEntry 17 }

ipUnityAsrChannelsISInCard 	OBJECT-TYPE        
        SYNTAX Integer32
        MAX-ACCESS read-only
        STATUS current
        DESCRIPTION	"Total number of In-Service ASR channels in a particular card."
::= { ipUnityCardLevelResourceStatisticsEntry 18 }

ipUnityAsrChannelsActiveInCard 	OBJECT-TYPE        
        SYNTAX Integer32
        MAX-ACCESS read-only
        STATUS current
        DESCRIPTION		"Total number of active ASR channels in a particular card. "
::= { ipUnityCardLevelResourceStatisticsEntry 19 }

ipUnityVxmlChannelsAvailableInCard 	OBJECT-TYPE        
        SYNTAX Integer32
        MAX-ACCESS read-only
        STATUS current
        DESCRIPTION		"Total number of available vxml channels in a particular card. "
::= { ipUnityCardLevelResourceStatisticsEntry 20 }

ipUnityVxmlChannelsOOSInCard 	OBJECT-TYPE        
        SYNTAX Integer32
        MAX-ACCESS read-only
        STATUS current
        DESCRIPTION		"Total number of Out-Of-Service vxml channels in a particular card. "
::= { ipUnityCardLevelResourceStatisticsEntry 21 }

ipUnityVxmlChannelsISInCard 	OBJECT-TYPE        
        SYNTAX Integer32
        MAX-ACCESS read-only
        STATUS current
        DESCRIPTION	"Total number of In-Service vxml channels in a particular card."
::= { ipUnityCardLevelResourceStatisticsEntry 22 }

ipUnityVxmlChannelsActiveInCard 	OBJECT-TYPE        
        SYNTAX Integer32
        MAX-ACCESS read-only
        STATUS current
        DESCRIPTION		"Total number of active vxml channels in a particular card. "
::= { ipUnityCardLevelResourceStatisticsEntry 23 }

ipUnityHttpChannelsAvailableInCard 	OBJECT-TYPE        
        SYNTAX Integer32
        MAX-ACCESS read-only
        STATUS current
        DESCRIPTION		"Total number of available HTTP channels in a particular card. "
::= { ipUnityCardLevelResourceStatisticsEntry 24 }

ipUnityHttpChannelsOOSInCard 	OBJECT-TYPE        
        SYNTAX Integer32
        MAX-ACCESS read-only
        STATUS current
        DESCRIPTION		"Total number of Out-Of-Service HTTP channels in a particular card. "
::= { ipUnityCardLevelResourceStatisticsEntry 25 }

ipUnityHttpChannelsISInCard 	OBJECT-TYPE        
        SYNTAX Integer32
        MAX-ACCESS read-only
        STATUS current
        DESCRIPTION	"Total number of In-Service HTTP channels in a particular card."
::= { ipUnityCardLevelResourceStatisticsEntry 26 }

ipUnityHttpChannelsActiveInCard 	OBJECT-TYPE        
        SYNTAX Integer32
        MAX-ACCESS read-only
        STATUS current
        DESCRIPTION		"Total number of active HTTP channels in a particular card. "
::= { ipUnityCardLevelResourceStatisticsEntry 27 }

-- bank level statistics table


ipUnityBankLevelResourceStatisticsTable   OBJECT-TYPE
        SYNTAX SEQUENCE OF IpUnityBankLevelResourceStatisticsEntry
        MAX-ACCESS not-accessible
        STATUS current
        DESCRIPTION    "..."
 ::= { ipUnityResourceStatistics 3 }

ipUnityBankLevelResourceStatisticsEntry  OBJECT-TYPE
    SYNTAX IpUnityBankLevelResourceStatisticsEntry
    MAX-ACCESS not-accessible
    STATUS current
    DESCRIPTION
        "..."
    INDEX      { ipUnityCardIndex, ipUnityBankIndex }
    ::= { ipUnityBankLevelResourceStatisticsTable  1 }

IpUnityBankLevelResourceStatisticsEntry ::= SEQUENCE {
		ipUnityModulesAvailableInBank 	    Integer32,
		ipUnityModulesOOSInBank 				Integer32,
		ipUnityModulesISInBank 	       		Integer32,
		ipUnityConfChannelsAvailableInBank 	Integer32,
		ipUnityConfChannelsOOSInBank 			Integer32,
		ipUnityConfChannelsISInBank 			Integer32,
		ipUnityConfChannelsActiveInBank 		Integer32,
		ipUnityIvrChannelsAvailableInBank		Integer32,
		ipUnityIvrChannelsOOSInBank 			Integer32,
		ipUnityIvrChannelsISInBank 			Integer32,
		ipUnityIvrChannelsActiveInBank 	Integer32,
		ipUnityAhConfChannelsAvailableInBank 	Integer32,
		ipUnityAhConfChannelsOOSInBank 			Integer32,
		ipUnityAhConfChannelsISInBank 			Integer32,
		ipUnityAhConfChannelsActiveInBank 		Integer32,
		ipUnityAsrChannelsAvailableInBank 	Integer32,
		ipUnityAsrChannelsOOSInBank 			Integer32,
		ipUnityAsrChannelsISInBank 			Integer32,
		ipUnityAsrChannelsActiveInBank 		Integer32,
		ipUnityVxmlChannelsAvailableInBank 	Integer32,
		ipUnityVxmlChannelsOOSInBank 			Integer32,
		ipUnityVxmlChannelsISInBank 			Integer32,
		ipUnityVxmlChannelsActiveInBank 		Integer32,
		ipUnityHttpChannelsAvailableInBank 	Integer32,
		ipUnityHttpChannelsOOSInBank 			Integer32,
		ipUnityHttpChannelsISInBank 			Integer32,
		ipUnityHttpChannelsActiveInBank 		Integer32
}

ipUnityModulesAvailableInBank 	OBJECT-TYPE        
        SYNTAX Integer32 
        MAX-ACCESS read-only
        STATUS current
        DESCRIPTION		"Total number of modules (e.g. DSP resources) available in the bank."
::= { ipUnityBankLevelResourceStatisticsEntry 1 }

ipUnityModulesOOSInBank 	OBJECT-TYPE        
        SYNTAX Integer32 
        MAX-ACCESS read-only
        STATUS current
        DESCRIPTION 		"Total number of out-of-service modules (e.g. DSP resources) in the bank." 
::= { ipUnityBankLevelResourceStatisticsEntry 2 }

ipUnityModulesISInBank 	OBJECT-TYPE        
        SYNTAX Integer32 
        MAX-ACCESS read-only
        STATUS current
        DESCRIPTION 		"Total number of in-service modules (e.g. DSP resources) in the bank."
::= { ipUnityBankLevelResourceStatisticsEntry 3 }

ipUnityConfChannelsAvailableInBank 	OBJECT-TYPE        
        SYNTAX Integer32 
        MAX-ACCESS read-only
        STATUS current
        DESCRIPTION		"Total number of available CONF-AH channels in each module (DSP)"
::= { ipUnityBankLevelResourceStatisticsEntry 4 }

ipUnityConfChannelsOOSInBank 	OBJECT-TYPE        
        SYNTAX Integer32
        MAX-ACCESS read-only
        STATUS current
        DESCRIPTION		"Total number of Out-Of-Service Conference channels in each module (DSP)"
::= { ipUnityBankLevelResourceStatisticsEntry 5 }

ipUnityConfChannelsISInBank 	OBJECT-TYPE        
        SYNTAX Integer32
        MAX-ACCESS read-only
        STATUS current
        DESCRIPTION	"Total number of In-Service CONF channels in each module (DSP)."
::= { ipUnityBankLevelResourceStatisticsEntry 6 }

ipUnityConfChannelsActiveInBank 	OBJECT-TYPE        
        SYNTAX Integer32
        MAX-ACCESS read-only
        STATUS current
        DESCRIPTION		"Total number of available CONF channels in each module (DSP)"
::= { ipUnityBankLevelResourceStatisticsEntry 7 }

ipUnityIvrChannelsAvailableInBank 	OBJECT-TYPE        
        SYNTAX Integer32
        MAX-ACCESS read-only
        STATUS current
        DESCRIPTION		"Total number of available IVR channels in each module (DSP)"
::= { ipUnityBankLevelResourceStatisticsEntry 8 }

ipUnityIvrChannelsOOSInBank 	OBJECT-TYPE        
        SYNTAX Integer32
        MAX-ACCESS read-only
        STATUS current
        DESCRIPTION		"Total number of Out-Of-Service IVR channels in each module (DSP)"
::= { ipUnityBankLevelResourceStatisticsEntry 9 }

ipUnityIvrChannelsISInBank 	OBJECT-TYPE        
        SYNTAX Integer32
        MAX-ACCESS read-only
        STATUS current
        DESCRIPTION	"Total number of In-Service IVR channels in each module (DSP)."
::= { ipUnityBankLevelResourceStatisticsEntry 10 }

ipUnityIvrChannelsActiveInBank 	OBJECT-TYPE        
        SYNTAX Integer32
        MAX-ACCESS read-only
        STATUS current
        DESCRIPTION	"Total number of In-Service IVR channels in each module (DSP)."
::= { ipUnityBankLevelResourceStatisticsEntry 11 }

ipUnityAhConfChannelsAvailableInBank    OBJECT-TYPE
        SYNTAX Integer32
        MAX-ACCESS read-only
        STATUS current
        DESCRIPTION     "Total number of available CONF-AH channels in each module (DSP)"
::= { ipUnityBankLevelResourceStatisticsEntry 12 }

ipUnityAhConfChannelsOOSInBank  OBJECT-TYPE
        SYNTAX Integer32
        MAX-ACCESS read-only
        STATUS current
        DESCRIPTION     "Total number of Out-Of-Service CONF-AH channels in each module (DSP)"
::= { ipUnityBankLevelResourceStatisticsEntry 13 }

ipUnityAhConfChannelsISInBank   OBJECT-TYPE
        SYNTAX Integer32
        MAX-ACCESS read-only
        STATUS current
        DESCRIPTION "Total number of In-Service CONF-AH channels in each module (DSP)."
::= { ipUnityBankLevelResourceStatisticsEntry 14 }

ipUnityAhConfChannelsActiveInBank   OBJECT-TYPE
        SYNTAX Integer32
        MAX-ACCESS read-only
        STATUS current
        DESCRIPTION     "Total number of available CONF-AH channels in each module (DSP)"
::= { ipUnityBankLevelResourceStatisticsEntry 15 }

ipUnityAsrChannelsAvailableInBank   OBJECT-TYPE
        SYNTAX Integer32
        MAX-ACCESS read-only
        STATUS current
        DESCRIPTION     "Total number of available ASR channels in each module (DSP)"
::= { ipUnityBankLevelResourceStatisticsEntry 16 }

ipUnityAsrChannelsOOSInBank     OBJECT-TYPE
        SYNTAX Integer32
        MAX-ACCESS read-only
        STATUS current
        DESCRIPTION     "Total number of Out-Of-Service ASR channels in each module (DSP)"
::= { ipUnityBankLevelResourceStatisticsEntry 17 }

ipUnityAsrChannelsISInBank  OBJECT-TYPE
        SYNTAX Integer32
        MAX-ACCESS read-only
        STATUS current
        DESCRIPTION "Total number of In-Service ASR channels in each module (DSP)."
::= { ipUnityBankLevelResourceStatisticsEntry 18 }

ipUnityAsrChannelsActiveInBank  OBJECT-TYPE
        SYNTAX Integer32
        MAX-ACCESS read-only
        STATUS current
        DESCRIPTION     "Total number of available ASR channels in each module (DSP)"
::= { ipUnityBankLevelResourceStatisticsEntry 19 }

ipUnityVxmlChannelsAvailableInBank  OBJECT-TYPE
        SYNTAX Integer32
        MAX-ACCESS read-only
        STATUS current
        DESCRIPTION     "Total number of available Vxml channels in each module (DSP)"
::= { ipUnityBankLevelResourceStatisticsEntry 20 }

ipUnityVxmlChannelsOOSInBank    OBJECT-TYPE
        SYNTAX Integer32
        MAX-ACCESS read-only
        STATUS current
        DESCRIPTION     "Total number of Out-Of-Service Vxml channels in each module (DSP)"
::= { ipUnityBankLevelResourceStatisticsEntry 21 }

ipUnityVxmlChannelsISInBank     OBJECT-TYPE
        SYNTAX Integer32
        MAX-ACCESS read-only
        STATUS current
        DESCRIPTION "Total number of In-Service Vxml channels in each module (DSP)."
::= { ipUnityBankLevelResourceStatisticsEntry 22 }

ipUnityVxmlChannelsActiveInBank     OBJECT-TYPE
        SYNTAX Integer32
        MAX-ACCESS read-only
        STATUS current
        DESCRIPTION     "Total number of available Vxml channels in each module (DSP)"
::= { ipUnityBankLevelResourceStatisticsEntry 23 }

ipUnityHttpChannelsAvailableInBank  OBJECT-TYPE
        SYNTAX Integer32
        MAX-ACCESS read-only
        STATUS current
        DESCRIPTION     "Total number of available HTTP channels in each module (DSP)"
::= { ipUnityBankLevelResourceStatisticsEntry 24 }

ipUnityHttpChannelsOOSInBank    OBJECT-TYPE
        SYNTAX Integer32
        MAX-ACCESS read-only
        STATUS current
        DESCRIPTION     "Total number of Out-Of-Service HTTP channels in each module (DSP)"
::= { ipUnityBankLevelResourceStatisticsEntry 25 }

ipUnityHttpChannelsISInBank     OBJECT-TYPE
        SYNTAX Integer32
        MAX-ACCESS read-only
        STATUS current
        DESCRIPTION "Total number of In-Service HTTP channels in each module (DSP)."
::= { ipUnityBankLevelResourceStatisticsEntry 26 }

ipUnityHttpChannelsActiveInBank     OBJECT-TYPE
        SYNTAX Integer32
        MAX-ACCESS read-only
        STATUS current
        DESCRIPTION     "Total number of available HTTP channels in each module (DSP)"
::= { ipUnityBankLevelResourceStatisticsEntry 27 }

--In service Module statistics
ipUnityModuleStatistics   OBJECT IDENTIFIER ::= { ipUnityResourceStatistics 4 }

ipUnityNumActDspInService 	OBJECT-TYPE        
        SYNTAX INTEGER
        MAX-ACCESS read-only
        STATUS current
        DESCRIPTION		
		"Total number of DSP in service."
::= { ipUnityModuleStatistics 1 }

ipUnityNumActDspOutOfService 	OBJECT-TYPE        
        SYNTAX INTEGER
        MAX-ACCESS read-only
        STATUS current
        DESCRIPTION 		
		"Total number of DSP out of service." 
::= { ipUnityModuleStatistics 2 }

ipUnityNumActDspOnSystem 	OBJECT-TYPE        
        SYNTAX INTEGER
        MAX-ACCESS read-only
        STATUS current
        DESCRIPTION 		
		"Total number of DSP in the system."
::= { ipUnityModuleStatistics 3 }

ipUnityNumStbDspInService 	OBJECT-TYPE        
        SYNTAX INTEGER
        MAX-ACCESS read-only
        STATUS current
        DESCRIPTION 		
                " Total number of standby DSP in Service."
::= { ipUnityModuleStatistics 4 }

ipUnityNumStbDspOutOfService	OBJECT-TYPE        
        SYNTAX INTEGER
        MAX-ACCESS read-only
        STATUS current
        DESCRIPTION 		
                "Total number of standby DSP out of Service."
::= { ipUnityModuleStatistics 5 }

ipUnityNumStbDspOnSystem    OBJECT-TYPE
        SYNTAX INTEGER
        MAX-ACCESS read-only
        STATUS current
        DESCRIPTION 		
                " Total number of standby DSP in the system." 
::= { ipUnityModuleStatistics 6 }

ipUnityNumAsrInService 	OBJECT-TYPE        
        SYNTAX INTEGER
        MAX-ACCESS read-only
        STATUS current
        DESCRIPTION		
		"Total number of ASR in service."
::= { ipUnityModuleStatistics 7 }

ipUnityNumAsrOutOfService 	OBJECT-TYPE        
        SYNTAX INTEGER
        MAX-ACCESS read-only
        STATUS current
        DESCRIPTION 		
		"Total number of ASR out of service." 
::= { ipUnityModuleStatistics 8 }

ipUnityNumAsrOnSystem 	OBJECT-TYPE        
        SYNTAX INTEGER
        MAX-ACCESS read-only
        STATUS current
        DESCRIPTION 		
		"Total number of ASR in the system."
::= { ipUnityModuleStatistics 9 }

ipUnityNumIcmInService 	OBJECT-TYPE        
        SYNTAX INTEGER
        MAX-ACCESS read-only
        STATUS current
        DESCRIPTION 
               " Total number of ICM in service."
::= { ipUnityModuleStatistics 10 }

ipUnityNumIcmOutOfService	OBJECT-TYPE        
        SYNTAX INTEGER
        MAX-ACCESS read-only
        STATUS current
        DESCRIPTION 		
               " Total number of ICM out of service."
::= { ipUnityModuleStatistics 11 }

ipUnityNumIcmOnSystem    OBJECT-TYPE
        SYNTAX INTEGER
        MAX-ACCESS read-only
        STATUS current
        DESCRIPTION 		
               " Total number of ICM in the system."
::= { ipUnityModuleStatistics 12 }

ipUnityNumHttpInService 	OBJECT-TYPE        
        SYNTAX INTEGER
        MAX-ACCESS read-only
        STATUS current
        DESCRIPTION		
		"Total number of HTTP in service."
::= { ipUnityModuleStatistics 13 }

ipUnityNumHttpOutOfService 	OBJECT-TYPE        
        SYNTAX INTEGER
        MAX-ACCESS read-only
        STATUS current
        DESCRIPTION 		
		"Total number of HTTP out of service." 
::= { ipUnityModuleStatistics 14 }

ipUnityNumHttpOnSystem 	OBJECT-TYPE        
        SYNTAX INTEGER
        MAX-ACCESS read-only
        STATUS current
        DESCRIPTION 		
		"Total number of HTTP services in the system."
::= { ipUnityModuleStatistics 15 }

ipUnityNumVxmlInService 	OBJECT-TYPE        
        SYNTAX INTEGER
        MAX-ACCESS read-only
        STATUS current
        DESCRIPTION 		
               " Total number of vxml channels in service."
::= { ipUnityModuleStatistics 16 }

ipUnityNumVxmlOutOfService	OBJECT-TYPE        
        SYNTAX INTEGER
        MAX-ACCESS read-only
        STATUS current
        DESCRIPTION 		
               " Total number of vxml channels out of service."
::= { ipUnityModuleStatistics 17 }

ipUnityNumVxmlOnSystem    OBJECT-TYPE
        SYNTAX INTEGER
        MAX-ACCESS read-only
        STATUS current
        DESCRIPTION 		
               " Total number of out-of-service vxml channels in the system."
::= { ipUnityModuleStatistics 18 }

--Partition rersource statistics

ipUnityPartitionLevelResourceStatisticsTable   OBJECT-TYPE
        SYNTAX SEQUENCE OF IpUnityPartitionLevelResourceStatisticsEntry
        MAX-ACCESS not-accessible
        STATUS current
        DESCRIPTION " A table containing partition resource in the Media Server."
 ::= { ipUnityResourceStatistics 5 }

ipUnityPartitionLevelResourceStatisticsEntry  OBJECT-TYPE
    SYNTAX IpUnityPartitionLevelResourceStatisticsEntry
    MAX-ACCESS not-accessible
    STATUS current
    DESCRIPTION
        "An entry in the resource statistics table."
    INDEX      { ipUnityPartitionIndex, ipUnityPartitionResourceType }
    ::= { ipUnityPartitionLevelResourceStatisticsTable  1 }

IpUnityPartitionLevelResourceStatisticsEntry ::= SEQUENCE {
		ipUnityNumBusyChannels                 Integer32,
		ipUnityNumTotalConfiguredChannels      Integer32
}

ipUnityNumBusyChannels 	OBJECT-TYPE        
        SYNTAX Integer32
        MAX-ACCESS read-only
        STATUS current
        DESCRIPTION		"Total number of busy channels for a partition."
::= { ipUnityPartitionLevelResourceStatisticsEntry 1 }

ipUnityNumTotalConfiguredChannels 	OBJECT-TYPE        
        SYNTAX Integer32
        MAX-ACCESS read-only
        STATUS current
        DESCRIPTION		"Total number of configured channels for a partition."
::= { ipUnityPartitionLevelResourceStatisticsEntry 2 }

-- System statistics

ipUnityNumLongDurationCallsDetected OBJECT-TYPE        
        SYNTAX Counter32
        MAX-ACCESS read-only
        STATUS current
        DESCRIPTION	"Number of hung calls that are detected by the system (RSVD too long)."
::= { ipUnitySystemStatistics 1 }

ipUnityNumLongDurationCallsRecovered OBJECT-TYPE        
        SYNTAX Counter32
        MAX-ACCESS read-only
        STATUS current
        DESCRIPTION "Number of hung connections that are corrected by the system (BUSY too long)."
::= { ipUnitySystemStatistics 2 }

ipUnityNumHungChannels OBJECT-TYPE        
        SYNTAX Counter32
        MAX-ACCESS read-only
        STATUS current
        DESCRIPTION "Number of lockout channels that are detected by the 
system (LKUP)."
::= { ipUnitySystemStatistics 3 }

ipUnityNumLockupDetected OBJECT-TYPE        
        SYNTAX Counter32
        MAX-ACCESS read-only
        STATUS current
        DESCRIPTION "Number of lockout channels that are detected by the 
system (LKUP)."
::= { ipUnitySystemStatistics 4 }

ipUnityNumLockupRecovered OBJECT-TYPE        
        SYNTAX Counter32
        MAX-ACCESS read-only
        STATUS current
        DESCRIPTION "Number of lockout channels that are corrected by the 
system (LKUP)."
::= { ipUnitySystemStatistics 5 }

ipUnityNumSccTaskSuspend OBJECT-TYPE        
        SYNTAX Counter32
        MAX-ACCESS read-only
        STATUS current
        DESCRIPTION "Number of task suspend occurences in the SCC."
::= { ipUnitySystemStatistics 6 }

ipUnityPeakSession OBJECT-TYPE        
        SYNTAX Counter32
        MAX-ACCESS read-only
        STATUS current
        DESCRIPTION "Number of peak sessions."
::= { ipUnitySystemStatistics 7 }

ipUnityPeakCpu OBJECT-TYPE        
        SYNTAX Counter32
        MAX-ACCESS read-only
        STATUS current
        DESCRIPTION "Peak cpu."
::= { ipUnitySystemStatistics 8 }

ipUnityPeakCps OBJECT-TYPE        
        SYNTAX Counter32
        MAX-ACCESS read-only
        STATUS current
        DESCRIPTION "Peak cps."
::= { ipUnitySystemStatistics 9 }

ipUnityPeakSipCps OBJECT-TYPE        
        SYNTAX Counter32
        MAX-ACCESS read-only
        STATUS current
        DESCRIPTION "Peak Sip cps."
::= { ipUnitySystemStatistics 10 }

ipUnityCallLogIndex OBJECT-TYPE        
        SYNTAX Counter32
        MAX-ACCESS read-only
        STATUS current
        DESCRIPTION "Call log index."
::= { ipUnitySystemStatistics 11 }

-- new statistics groups for release 2.0

ipUnityASRStatistics		OBJECT IDENTIFIER ::= { ipUnityStatistics 5 }
ipUnityHttpStatistics		OBJECT IDENTIFIER ::= { ipUnityStatistics 6 }
ipUnityHttpServerStatistics	OBJECT IDENTIFIER ::= { ipUnityHttpStatistics 1 }
ipUnityHttpCacheStatistics	OBJECT IDENTIFIER ::= { ipUnityHttpStatistics 2 }
ipUnityVxmlStatistics		OBJECT IDENTIFIER ::= { ipUnityStatistics 7 }
ipUnitySipStatistics		OBJECT IDENTIFIER ::= { ipUnityStatistics 8 }
ipUnitySipCallStatistics	OBJECT IDENTIFIER ::= { ipUnityStatistics 9 }
ipUnityErrorStatistics	        OBJECT IDENTIFIER ::= { ipUnityStatistics 10}
ipUnityMegacoStatistics		OBJECT IDENTIFIER ::= { ipUnityStatistics 11 }
ipUnityMegacoCallStatistics	OBJECT IDENTIFIER ::= { ipUnityStatistics 12 }
ipUnityVideoStatistics	        OBJECT IDENTIFIER ::= { ipUnityStatistics 13 }
ipUnityTTSStatistics	        OBJECT IDENTIFIER ::= { ipUnityStatistics 14 }
msmlCallStatistics	        OBJECT IDENTIFIER ::= { ipUnityStatistics 15 }
msmlConfStatistics	        OBJECT IDENTIFIER ::= { ipUnityStatistics 16 }
msmlDialogStatistics	        OBJECT IDENTIFIER ::= { ipUnityStatistics 17 }

-- ASR Statistics

ipUnityAsrUtilization		OBJECT-TYPE
        SYNTAX INTEGER (0..100)
        MAX-ACCESS read-only
        STATUS current
        DESCRIPTION
                "The percentage utilization of the ASR engine."
	::= { ipUnityASRStatistics 1 }

ipUnityAsrAllocateAttempts	OBJECT-TYPE
	SYNTAX	Counter32
      MAX-ACCESS read-only
      STATUS current
      DESCRIPTION
                "The number of ASR allocate attempts."
    ::= { ipUnityASRStatistics 2 }

ipUnityAsrAllocateSuccesses	OBJECT-TYPE
	SYNTAX	Counter32
     	MAX-ACCESS read-only
      STATUS current
      DESCRIPTION
                "The number of ASR allocate successes."
    ::= { ipUnityASRStatistics 3 }

ipUnityAsrAllocateFailures	OBJECT-TYPE
	SYNTAX	Counter32
      MAX-ACCESS read-only
      STATUS current
      DESCRIPTION
                "The number of ASR allocate failures."
    ::= { ipUnityASRStatistics 4 }

ipUnityAsrActiveAttempts	OBJECT-TYPE
	SYNTAX	Counter32
      MAX-ACCESS read-only
      STATUS current
      DESCRIPTION
                "The number of ASR active attempts."
    ::= { ipUnityASRStatistics 5 }

ipUnityAsrActiveSuccesses	OBJECT-TYPE
	SYNTAX	Counter32
     	MAX-ACCESS read-only
      STATUS current
      DESCRIPTION
                "The number of ASR active successes."
    ::= { ipUnityASRStatistics 6 }

ipUnityAsrActiveFailures	OBJECT-TYPE
	SYNTAX	Counter32
      MAX-ACCESS read-only
      STATUS current
      DESCRIPTION
                "The number of ASR active failures."
    ::= { ipUnityASRStatistics 7 }

ipUnityAsrRecognizeAttempts	OBJECT-TYPE
	SYNTAX	Counter32
      MAX-ACCESS read-only
      STATUS current
      DESCRIPTION
                "The number of ASR recognize attempts."
    ::= { ipUnityASRStatistics 8 }

ipUnityAsrRecognizeSuccesses	OBJECT-TYPE
	SYNTAX	Counter32
     	MAX-ACCESS read-only
      STATUS current
      DESCRIPTION
                "The number of ASR recognize successes."
    ::= { ipUnityASRStatistics 9 }

ipUnityAsrRecognizeStops	OBJECT-TYPE
	SYNTAX	Counter32
      MAX-ACCESS read-only
      STATUS current
      DESCRIPTION
                "The number of ASR recognize stops."
    ::= { ipUnityASRStatistics 10 }

ipUnityAsrRecognizeRejections	OBJECT-TYPE
	SYNTAX	Counter32
      MAX-ACCESS read-only
      STATUS current
      DESCRIPTION
                "The number of ASR recognize rejections."
    ::= { ipUnityASRStatistics 11 }

-- HTTP server table statistics

ipUnityHttpServerTable		OBJECT-TYPE
        SYNTAX SEQUENCE OF IpUnityHttpServerEntry
        MAX-ACCESS not-accessible
        STATUS current
        DESCRIPTION
                "The table containing the HTTP server related data."
	::= { ipUnityHttpServerStatistics 1 }

ipUnityHttpServerEntry  OBJECT-TYPE
    SYNTAX IpUnityHttpServerEntry
    MAX-ACCESS not-accessible
    STATUS current
    DESCRIPTION
        	"An entry in the HTTP server related data table containing the set of 
		data for that server."
    INDEX      { ipUnityHttpServerAddress }
    ::= { ipUnityHttpServerTable 1 }

IpUnityHttpServerEntry ::= SEQUENCE {
	ipUnityHttpServerAddress			IpAddress,
	ipUnityHttpServerConnectionFailures		Counter32,
	ipUnityHttpServerUnexpectedConnectionCloses	Counter32,
	ipUnityHttpServerFetches			Counter32,
	ipUnityHttpServerFetchErrors			Counter32,
	ipUnityHttpServerAverageThroughput		Integer32,
	ipUnityHttpServerRejectionsForPlayingAnnc	Counter32,
	ipUnityHttpServerStreamingBufferUnderruns	Counter32
	}

ipUnityHttpServerAddress	OBJECT-TYPE
        SYNTAX IpAddress	
        MAX-ACCESS read-only
        STATUS current
        DESCRIPTION
                "The IP Address of HTTP Server."
    ::= { ipUnityHttpServerEntry 1 }

ipUnityHttpServerConnectionFailures	OBJECT-TYPE
        SYNTAX Counter32
        MAX-ACCESS read-only
        STATUS current
        DESCRIPTION
                "The number of connection failures for this HTTP server."
    ::= { ipUnityHttpServerEntry 2 }

ipUnityHttpServerUnexpectedConnectionCloses	OBJECT-TYPE
        SYNTAX 	Counter32
        MAX-ACCESS read-only
        STATUS current
        DESCRIPTION
                "The number of unexpected HTTP connection closes done by the server."
    ::= { ipUnityHttpServerEntry 3 }

ipUnityHttpServerFetches	OBJECT-TYPE
	SYNTAX 	Counter32
        MAX-ACCESS read-only
        STATUS current
        DESCRIPTION
                "The number of HTTP fetches initiated on this server."
    ::= { ipUnityHttpServerEntry 4 }

ipUnityHttpServerFetchErrors	OBJECT-TYPE
	SYNTAX 	Counter32
        MAX-ACCESS read-only
        STATUS current
        DESCRIPTION
                "The number of fetch errors at this HTTP Server."
    ::= { ipUnityHttpServerEntry 5 }

ipUnityHttpServerAverageThroughput	OBJECT-TYPE
	SYNTAX	Integer32
	UNITS	"kilobits per second"
        MAX-ACCESS read-only
        STATUS current
        DESCRIPTION
                "The Average Throughput on this HTTP server in kilobits per second."
    ::= { ipUnityHttpServerEntry 6 }

ipUnityHttpServerRejectionsForPlayingAnnc	OBJECT-TYPE
	SYNTAX	Counter32
        MAX-ACCESS read-only
        STATUS current
        DESCRIPTION
                "The number of times announcement playing from this HTTP server was rejected."
    ::= { ipUnityHttpServerEntry 7 }

ipUnityHttpServerStreamingBufferUnderruns	OBJECT-TYPE
	SYNTAX	Counter32
        MAX-ACCESS read-only
        STATUS current
        DESCRIPTION
                "The number of times there were streaming buffer (pre-play buffer) underruns 
		while playing from this server."
    ::= { ipUnityHttpServerEntry 8 }

-- cache statistics

ipUnityHttpNumCacheHits		OBJECT-TYPE
	SYNTAX	Counter32	
        MAX-ACCESS read-only
        STATUS current
        DESCRIPTION
                "The number of HTTP-G4 global cache hits."
	::= { ipUnityHttpCacheStatistics 1 }

ipUnityHttpNumCacheMisses	OBJECT-TYPE
	SYNTAX	Counter32	
        MAX-ACCESS read-only
        STATUS current
        DESCRIPTION
                "The number of HTTP-G4 global cache misses."
	::= { ipUnityHttpCacheStatistics 2 }

--ipUnityHttpNumTimesCacheLowWatermarkHit	OBJECT-TYPE
--	SYNTAX	Counter32
--        MAX-ACCESS read-only
--        STATUS obsolete
--        DESCRIPTION
--                "The number of times low watermark is hit on the HTTP-G4 global cache."
--	::= { ipUnityHttpCacheStatistics 3 }

ipUnityHttpNumTimesCacheHighWatermarkHits	OBJECT-TYPE
	SYNTAX	Counter32	
        MAX-ACCESS read-only
        STATUS current
        DESCRIPTION
                "The number of times high watermark is hit on the HTTP-G4 global cache."
	::= { ipUnityHttpCacheStatistics 4 }


-- VXML statistics

ipUnityVxmlOpenRequests		OBJECT-TYPE
        SYNTAX Counter32
        MAX-ACCESS read-only
        STATUS current
        DESCRIPTION
                "The number of VXML open requests made."
        ::= { ipUnityVxmlStatistics 1 }

ipUnityVxmlOpenSuccesses	OBJECT-TYPE
        SYNTAX Counter32
        MAX-ACCESS read-only
        STATUS current
        DESCRIPTION
                "The number of successful VXML open attempts made."
        ::= { ipUnityVxmlStatistics 2 }

ipUnityVxmlOpenFailures		OBJECT-TYPE
        SYNTAX Counter32
        MAX-ACCESS read-only
        STATUS current
        DESCRIPTION
                "The number of failed VXML open attempts."
        ::= { ipUnityVxmlStatistics 3 }

ipUnityVxmlSystemErrors		OBJECT-TYPE
        SYNTAX Counter32
        MAX-ACCESS read-only
        STATUS current
        DESCRIPTION
                "The number of system errors in VXML."
        ::= { ipUnityVxmlStatistics 4 }

ipUnityVxmlHttpFetchFailures		OBJECT-TYPE
        SYNTAX Counter32
        MAX-ACCESS read-only
        STATUS current
        DESCRIPTION
                "The number of HTTP fetch failures in VXML."
        ::= { ipUnityVxmlStatistics 5 }

ipUnityVxmlMemoryFailures		OBJECT-TYPE
        SYNTAX Counter32
        MAX-ACCESS read-only
        STATUS current
        DESCRIPTION
                "The number of memory failures in VXML."
        ::= { ipUnityVxmlStatistics 6 }

ipUnityVxmlFatalFailures		OBJECT-TYPE
        SYNTAX Counter32
        MAX-ACCESS read-only
        STATUS current
        DESCRIPTION
                "The number of fatal failures in VXML."
        ::= { ipUnityVxmlStatistics 7 }

ipUnityVxmlMiscFailures		OBJECT-TYPE
        SYNTAX Counter32
        MAX-ACCESS read-only
        STATUS current
        DESCRIPTION
                "The number of miscellaneous failures in VXML."
        ::= { ipUnityVxmlStatistics 8 }

ipUnityVxmlStatReports		OBJECT-TYPE
        SYNTAX Counter32
        MAX-ACCESS read-only
        STATUS current
        DESCRIPTION
                "The number of stat reports in VXML."
        ::= { ipUnityVxmlStatistics 9 }

ipUnityVxmlStatResponses		OBJECT-TYPE
        SYNTAX Counter32
        MAX-ACCESS read-only
        STATUS current
        DESCRIPTION
                "The number of stat responses in VXML."
        ::= { ipUnityVxmlStatistics 10 }

ipUnityVxmlCloseRequests		OBJECT-TYPE
        SYNTAX Counter32
        MAX-ACCESS read-only
        STATUS current
        DESCRIPTION
                "The number of close requests in VXML."
        ::= { ipUnityVxmlStatistics 11 }

ipUnityVxmlCloseSuccesses		OBJECT-TYPE
        SYNTAX Counter32
        MAX-ACCESS read-only
        STATUS current
        DESCRIPTION
                "The number of close successes in VXML."
        ::= { ipUnityVxmlStatistics 12 }

ipUnityVxmlCloseFailures		OBJECT-TYPE
        SYNTAX Counter32
        MAX-ACCESS read-only
        STATUS current
        DESCRIPTION
                "The number of close failures in VXML."
        ::= { ipUnityVxmlStatistics 13 }

ipUnityVxmlPlayRequests		OBJECT-TYPE
        SYNTAX Counter32
        MAX-ACCESS read-only
        STATUS current
        DESCRIPTION
                "The number of play requests in VXML."
        ::= { ipUnityVxmlStatistics 14 }

ipUnityVxmlCollectRequests	OBJECT-TYPE
        SYNTAX Counter32
        MAX-ACCESS read-only
        STATUS current
        DESCRIPTION
                "The number of collect requests in VXML."
        ::= { ipUnityVxmlStatistics 15 }

ipUnityVxmlRecordRequests		OBJECT-TYPE
        SYNTAX Counter32
        MAX-ACCESS read-only
        STATUS current
        DESCRIPTION
                "The number of record requests in VXML."
        ::= { ipUnityVxmlStatistics 16 }

ipUnityVxmlRecognizeRequests		OBJECT-TYPE
        SYNTAX Counter32
        MAX-ACCESS read-only
        STATUS current
        DESCRIPTION
                "The number of recognize requests in VXML."
        ::= { ipUnityVxmlStatistics 17 }

ipUnityVxmlMediaASRRequests		OBJECT-TYPE
        SYNTAX Counter32
        MAX-ACCESS read-only
        STATUS current
        DESCRIPTION
                "The number of Media ASR requests in VXML."
        ::= { ipUnityVxmlStatistics 18 }

ipUnityVxmlPlayResponseSuccesses		OBJECT-TYPE
        SYNTAX Counter32
        MAX-ACCESS read-only
        STATUS current
        DESCRIPTION
                "The number of play response successes in VXML."
        ::= { ipUnityVxmlStatistics 19 }

ipUnityVxmlPlayResponseFailures		OBJECT-TYPE
        SYNTAX Counter32
        MAX-ACCESS read-only
        STATUS current
        DESCRIPTION
                "The number of play response failures in VXML."
        ::= { ipUnityVxmlStatistics 20 }

ipUnityVxmlCollectResponseSuccesses		OBJECT-TYPE
        SYNTAX Counter32
        MAX-ACCESS read-only
        STATUS current
        DESCRIPTION
                "The number of collect response successes in VXML."
        ::= { ipUnityVxmlStatistics 21 }

ipUnityVxmlCollectResponseFailures		OBJECT-TYPE
        SYNTAX Counter32
        MAX-ACCESS read-only
        STATUS current
        DESCRIPTION
                "The number of collect response failures in VXML."
        ::= { ipUnityVxmlStatistics 22 }

ipUnityVxmlRecordResponseSuccesses		OBJECT-TYPE
        SYNTAX Counter32
        MAX-ACCESS read-only
        STATUS current
        DESCRIPTION
                "The number of record response successes in VXML."
        ::= { ipUnityVxmlStatistics 23 }

ipUnityVxmlRecordResponseFailures		OBJECT-TYPE
        SYNTAX Counter32
        MAX-ACCESS read-only
        STATUS current
        DESCRIPTION
                "The number of record response failures in VXML."
        ::= { ipUnityVxmlStatistics 24 }

ipUnityVxmlRecognizeResponseSuccesses		OBJECT-TYPE
        SYNTAX Counter32
        MAX-ACCESS read-only
        STATUS current
        DESCRIPTION
                "The number of recognize response successes in VXML."
        ::= { ipUnityVxmlStatistics 25 }

ipUnityVxmlRecognizeResponseFailures		OBJECT-TYPE
        SYNTAX Counter32
        MAX-ACCESS read-only
        STATUS current
        DESCRIPTION
                "The number of recognize response failures in VXML."
        ::= { ipUnityVxmlStatistics 26 }

ipUnityVxmlMASRResponseSuccesses		OBJECT-TYPE
        SYNTAX Counter32
        MAX-ACCESS read-only
        STATUS current
        DESCRIPTION
                "The number of Media ASR response successes in VXML."
        ::= { ipUnityVxmlStatistics 27 }

ipUnityVxmlMASRResponseFailures		OBJECT-TYPE
        SYNTAX Counter32
        MAX-ACCESS read-only
        STATUS current
        DESCRIPTION
                "The number of Media ASR response failures in VXML."
        ::= { ipUnityVxmlStatistics 28 }

ipUnityVxmlTotalSessionsInProgress		OBJECT-TYPE
        SYNTAX Counter32
        MAX-ACCESS read-only
        STATUS current
        DESCRIPTION
                "The total number of VXML sessions in progress."
        ::= { ipUnityVxmlStatistics 29 }

ipUnityVxmlInvalidMessagesReceived		OBJECT-TYPE
        SYNTAX Counter32
        MAX-ACCESS read-only
        STATUS current
        DESCRIPTION
                "The number of invalid messages received in VXML."
        ::= { ipUnityVxmlStatistics 30 }

ipUnityVxmlSendMessageFailures		OBJECT-TYPE
        SYNTAX Counter32
        MAX-ACCESS read-only
        STATUS current
        DESCRIPTION
                "The number of send message failures in VXML."
        ::= { ipUnityVxmlStatistics 31 }

ipUnityVxmlXferReq		OBJECT-TYPE
        SYNTAX Counter32
        MAX-ACCESS read-only
        STATUS current
        DESCRIPTION
                "The number of Xfer requests in VXML."
        ::= { ipUnityVxmlStatistics 32 }

ipUnityVxmlXferRespSuccess	OBJECT-TYPE
        SYNTAX Counter32
        MAX-ACCESS read-only
        STATUS current
        DESCRIPTION
                "The number of Xfer response Success in VXML."
        ::= { ipUnityVxmlStatistics 33 }

ipUnityVxmlXferRespFailure	OBJECT-TYPE
        SYNTAX Counter32
        MAX-ACCESS read-only
        STATUS current
        DESCRIPTION
                "The number of Xfer response failures in VXML."
        ::= { ipUnityVxmlStatistics 34 }

--SIP statistics

ipUnitySipTotalInvitesReceived		OBJECT-TYPE
        SYNTAX Counter32
        MAX-ACCESS read-only
        STATUS current
        DESCRIPTION
                "The total number of SIP invites that have been received by the Media Server."
	::= { ipUnitySipStatistics 1 }

ipUnitySipTotalInvitesOkRecieved		OBJECT-TYPE
        SYNTAX Counter32
        MAX-ACCESS read-only
        STATUS current
        DESCRIPTION
                "The number of SIP invites to which an OK response was sent by the Media Server."
	::= { ipUnitySipStatistics 2 }

ipUnitySipTotalInvitesSent		OBJECT-TYPE
        SYNTAX Counter32
        MAX-ACCESS read-only
        STATUS current
        DESCRIPTION
                "The total number of SIP invites that have been sent by the Media Server."
	::= { ipUnitySipStatistics 3 }

ipUnitySipTotalInvitesOkSent		OBJECT-TYPE
        SYNTAX Counter32
        MAX-ACCESS read-only
        STATUS current
        DESCRIPTION
                "The number of SIP invites sent for which an OK response was received by the Media Server."
	::= { ipUnitySipStatistics 4 }

ipUnitySipTotalReInvitesReceived		OBJECT-TYPE
        SYNTAX Counter32
        MAX-ACCESS read-only
        STATUS current
        DESCRIPTION
                "The total number of SIP ReInvites that have been received by the Media Server."
	::= { ipUnitySipStatistics 5 }

ipUnitySipTotalReInvitesOkRecieved		OBJECT-TYPE
        SYNTAX Counter32
        MAX-ACCESS read-only
        STATUS current
        DESCRIPTION
                "The number of SIP ReInvites to which an OK response was sent by the Media Server."
	::= { ipUnitySipStatistics 6 }

ipUnitySipTotalReInvitesSent		OBJECT-TYPE
        SYNTAX Counter32
        MAX-ACCESS read-only
        STATUS current
        DESCRIPTION
                "The total number of SIP ReInvites that have been sent by the Media Server."
	::= { ipUnitySipStatistics 7 }

ipUnitySipTotalReInvitesOkSent		OBJECT-TYPE
        SYNTAX Counter32
        MAX-ACCESS read-only
        STATUS current
        DESCRIPTION
                "The number of SIP ReInvites sent for which an OK response was received by the Media Server."
	::= { ipUnitySipStatistics 8 }

ipUnitySipTotalByesReceived		OBJECT-TYPE
        SYNTAX Counter32
        MAX-ACCESS read-only
        STATUS current
        DESCRIPTION
                "The total number of SIP Byes that have been received by the Media Server."
	::= { ipUnitySipStatistics 9 }

ipUnitySipTotalByesOkRecieved		OBJECT-TYPE
        SYNTAX Counter32
        MAX-ACCESS read-only
        STATUS current
        DESCRIPTION
                "The number of SIP Byes to which an OK response was sent by the Media Server."
	::= { ipUnitySipStatistics 10 }

ipUnitySipTotalByesSent		OBJECT-TYPE
        SYNTAX Counter32
        MAX-ACCESS read-only
        STATUS current
        DESCRIPTION
                "The total number of SIP Byes that have been sent by the Media Server."
	::= { ipUnitySipStatistics 11 }

ipUnitySipTotalByesOkSent		OBJECT-TYPE
        SYNTAX Counter32
        MAX-ACCESS read-only
        STATUS current
        DESCRIPTION
                "The number of SIP Byes sent for which an OK response was received by the Media Server."
	::= { ipUnitySipStatistics 12 }

ipUnitySipTotalCancelsReceived		OBJECT-TYPE
        SYNTAX Counter32
        MAX-ACCESS read-only
        STATUS current
        DESCRIPTION
                "The total number of SIP Cancels that have been received by the Media Server."
	::= { ipUnitySipStatistics 13 }

ipUnitySipTotalCancelsOkRecieved		OBJECT-TYPE
        SYNTAX Counter32
        MAX-ACCESS read-only
        STATUS current
        DESCRIPTION
                "The number of SIP Cancels to which an OK response was sent by the Media Server."
	::= { ipUnitySipStatistics 14 }

ipUnitySipTotalCancelsSent		OBJECT-TYPE
        SYNTAX Counter32
        MAX-ACCESS read-only
        STATUS current
        DESCRIPTION
                "The total number of SIP Cancels that have been sent by the Media Server."
	::= { ipUnitySipStatistics 15 }

ipUnitySipTotalCancelsOkSent		OBJECT-TYPE
        SYNTAX Counter32
        MAX-ACCESS read-only
        STATUS current
        DESCRIPTION
                "The number of SIP Cancels sent for which an OK response was received by the Media Server."
	::= { ipUnitySipStatistics 16 }

ipUnitySipTotalAcksReceived		OBJECT-TYPE
        SYNTAX Counter32
        MAX-ACCESS read-only
        STATUS current
        DESCRIPTION
                "The number of SIP acknowledgments that have been received by the Media Server."
	::= { ipUnitySipStatistics 17 }

ipUnitySipTotalAcksSent		OBJECT-TYPE
        SYNTAX Counter32
        MAX-ACCESS read-only
        STATUS current
        DESCRIPTION
                "The number of SIP acknowledgments that have been Sent by the Media Server."
	::= { ipUnitySipStatistics 18 }

ipUnitySipTotalOptions		OBJECT-TYPE
        SYNTAX Counter32
        MAX-ACCESS read-only
        STATUS current
        DESCRIPTION
                "The number of SIP options that have been received by the Media Server."
	::= { ipUnitySipStatistics 19 }


ipUnitySipTotalOptionsOk		OBJECT-TYPE
        SYNTAX Counter32
        MAX-ACCESS read-only
        STATUS current
        DESCRIPTION
                "The number of SIP options to which an OK response was sent by the Media Server."
	::= { ipUnitySipStatistics 20 }

ipUnitySipTotal1xxResponseCodesTransmitted		OBJECT-TYPE
        SYNTAX Counter32
        MAX-ACCESS read-only
        STATUS current
        DESCRIPTION
                "The number of SIP 1xx response codes transmitted by the Media Server."
	::= { ipUnitySipStatistics 21 }

ipUnitySipTotal1xxResponseCodesReceived		OBJECT-TYPE
        SYNTAX Counter32
        MAX-ACCESS read-only
        STATUS current
        DESCRIPTION
                "The number of SIP 1xx response codes received by the Media Server."
	::= { ipUnitySipStatistics 22 }

ipUnitySipTotal2xxResponseCodesTransmitted		OBJECT-TYPE
        SYNTAX Counter32
        MAX-ACCESS read-only
        STATUS current
        DESCRIPTION
                "The number of SIP 2xx response codes transmitted by the Media Server."
	::= { ipUnitySipStatistics 23 }

ipUnitySipTotal2xxResponseCodesReceived		OBJECT-TYPE
        SYNTAX Counter32
        MAX-ACCESS read-only
        STATUS current
        DESCRIPTION
                "The number of SIP 2xx response codes received by the Media Server."
	::= { ipUnitySipStatistics 24 }

ipUnitySipTotal3xxResponseCodesTransmitted		OBJECT-TYPE
        SYNTAX Counter32
        MAX-ACCESS read-only
        STATUS current
        DESCRIPTION
                "The number of SIP 3xx response codes transmitted by the Media Server."
	::= { ipUnitySipStatistics 25 }

ipUnitySipTotal3xxResponseCodesReceived		OBJECT-TYPE
        SYNTAX Counter32
        MAX-ACCESS read-only
        STATUS current
        DESCRIPTION
                "The number of SIP 3xx response codes received by the Media Server."
	::= { ipUnitySipStatistics 26 }

ipUnitySipTotal4xxResponseCodesTransmitted		OBJECT-TYPE
        SYNTAX Counter32
        MAX-ACCESS read-only
        STATUS current
        DESCRIPTION
                "The number of SIP 4xx response codes transmitted by the Media Server."
	::= { ipUnitySipStatistics 27 }

ipUnitySipTotal4xxResponseCodesReceived		OBJECT-TYPE
        SYNTAX Counter32
        MAX-ACCESS read-only
        STATUS current
        DESCRIPTION
                "The number of SIP 4xx response codes received by the Media Server."
	::= { ipUnitySipStatistics 28 }

ipUnitySipTotal5xxResponseCodesTransmitted		OBJECT-TYPE
        SYNTAX Counter32
        MAX-ACCESS read-only
        STATUS current
        DESCRIPTION
                "The number of SIP 5xx response codes transmitted by the Media Server."
	::= { ipUnitySipStatistics 29 }

ipUnitySipTotal5xxResponseCodesReceived		OBJECT-TYPE
        SYNTAX Counter32
        MAX-ACCESS read-only
        STATUS current
        DESCRIPTION
                "The number of SIP 5xx response codes received by the Media Server."
	::= { ipUnitySipStatistics 30 }

ipUnitySipTotal6xxResponseCodesTransmitted		OBJECT-TYPE
        SYNTAX Counter32
        MAX-ACCESS read-only
        STATUS current
        DESCRIPTION
                "The number of SIP 6xx response codes transmitted by the Media Server."
	::= { ipUnitySipStatistics 31 }


ipUnitySipTotal6xxResponseCodesReceived		OBJECT-TYPE
        SYNTAX Counter32
        MAX-ACCESS read-only
        STATUS current
        DESCRIPTION
                "The number of SIP 6xx response codes received by the Media Server."
	::= { ipUnitySipStatistics 32 }

ipUnitySipTotalRetransmissions		OBJECT-TYPE
        SYNTAX Counter32
        MAX-ACCESS read-only
        STATUS current
        DESCRIPTION
                "The number of SIP retransmissions done by the Media Server."
	::= { ipUnitySipStatistics 33 }

ipUnitySipTotalPrack		OBJECT-TYPE
        SYNTAX Counter32
        MAX-ACCESS read-only
        STATUS current
        DESCRIPTION
                "The total number of PRACKs received."
	::= { ipUnitySipStatistics 34 }

ipUnitySipTotalPrackOk		OBJECT-TYPE
        SYNTAX Counter32
        MAX-ACCESS read-only
        STATUS current
        DESCRIPTION
                "The total number of PRACKS OKs sent."
	::= { ipUnitySipStatistics 35 }

ipUnitySipTotalNotify		OBJECT-TYPE
        SYNTAX Counter32
        MAX-ACCESS read-only
        STATUS current
        DESCRIPTION
                "The total number of notify reveived."
	::= { ipUnitySipStatistics 36 }

ipUnitySipTotalNotifyOk		OBJECT-TYPE
        SYNTAX Counter32
        MAX-ACCESS read-only
        STATUS current
        DESCRIPTION
                "The total number of notify OK sent."
	::= { ipUnitySipStatistics 37 }

ipUnitySipTotalReferSent		OBJECT-TYPE
        SYNTAX Counter32
        MAX-ACCESS read-only
        STATUS current
        DESCRIPTION
                "The total number of REFER sent."
	::= { ipUnitySipStatistics 38 }

ipUnitySipTotalReferSentOk		OBJECT-TYPE
        SYNTAX Counter32
        MAX-ACCESS read-only
        STATUS current
        DESCRIPTION
                "The total number of REFER ok sent."
	::= { ipUnitySipStatistics 39 }

ipUnitySipTotalInfo		OBJECT-TYPE
        SYNTAX Counter32
        MAX-ACCESS read-only
        STATUS current
        DESCRIPTION
                "The total number of info received."
	::= { ipUnitySipStatistics 40 }

ipUnitySipTotalInfoOk		OBJECT-TYPE
        SYNTAX Counter32
        MAX-ACCESS read-only
        STATUS current
        DESCRIPTION
                "The total number of Info received ok sent."
	::= { ipUnitySipStatistics 41 }

ipUnitySipTotalInfoSent		OBJECT-TYPE
        SYNTAX Counter32
        MAX-ACCESS read-only
        STATUS current
        DESCRIPTION
                "The total number of Info sent."
	::= { ipUnitySipStatistics 42 }

ipUnitySipTotalInfoSentOk		OBJECT-TYPE
        SYNTAX Counter32
        MAX-ACCESS read-only
        STATUS current
        DESCRIPTION
                "The total number of Info sent ok."
	::= { ipUnitySipStatistics 43 }

ipUnitySipTotalSubscribeSent		OBJECT-TYPE
        SYNTAX Counter32
        MAX-ACCESS read-only
        STATUS current
        DESCRIPTION
                "The total number of SUBSCRIBE sent."
	::= { ipUnitySipStatistics 44 }

ipUnitySipTotalSubscribeSentOk		OBJECT-TYPE
        SYNTAX Counter32
        MAX-ACCESS read-only
        STATUS current
        DESCRIPTION
                "The total number of SUBSCRIBE ok received."
	::= { ipUnitySipStatistics 45 }

--SIP related call statistics

ipUnitySipCallChannelOpenAttempts		OBJECT-TYPE
        SYNTAX Counter32
        MAX-ACCESS read-only
        STATUS current
        DESCRIPTION
                "The number of channel open attempts for SIP calls."
	::= { ipUnitySipCallStatistics 1 }

ipUnitySipCallChannelOpenFailuresTotal		OBJECT-TYPE
        SYNTAX Counter32
        MAX-ACCESS read-only
        STATUS current
        DESCRIPTION
                "The total number of channel open failures for SIP calls."
	::= { ipUnitySipCallStatistics 2 }

ipUnitySipCallChannelAllocationFailures		OBJECT-TYPE
        SYNTAX Counter32
        MAX-ACCESS read-only
        STATUS current
        DESCRIPTION
                "The number of channel allocation failures for SIP calls."
	::= { ipUnitySipCallStatistics 3 }

ipUnitySipCallChannelOpenFailures		OBJECT-TYPE
        SYNTAX Counter32
        MAX-ACCESS read-only
        STATUS current
        DESCRIPTION
                "The number of channel open failures for SIP calls."
	::= { ipUnitySipCallStatistics 4 }

ipUnitySipCallChannelATMConnectionFailures		OBJECT-TYPE
        SYNTAX Counter32
        MAX-ACCESS read-only
        STATUS current
        DESCRIPTION
                "The number of channel ATM connection failures for SIP calls."
	::= { ipUnitySipCallStatistics 5 }

ipUnitySipCallChannelModifyAttempts		OBJECT-TYPE
        SYNTAX Counter32
        MAX-ACCESS read-only
        STATUS current
        DESCRIPTION
                "The number of channel modify attempts for SIP calls."
	::= { ipUnitySipCallStatistics 6 }

ipUnitySipCallChannelModifyFailures		OBJECT-TYPE
        SYNTAX Counter32
        MAX-ACCESS read-only
        STATUS current
        DESCRIPTION
                "The number of channel modify failures for SIP calls."
	::= { ipUnitySipCallStatistics 7 }

ipUnitySipCallChannelServiceAttempts		OBJECT-TYPE
        SYNTAX Counter32
        MAX-ACCESS read-only
        STATUS current
        DESCRIPTION
                "The number of channel service attempts for SIP calls."
	::= { ipUnitySipCallStatistics 8 }

ipUnitySipCallChannelServiceFailures		OBJECT-TYPE
        SYNTAX Counter32
        MAX-ACCESS read-only
        STATUS current
        DESCRIPTION
                "The number of channel service failures for SIP calls."
	::= { ipUnitySipCallStatistics 9 }

ipUnitySipCallChannelCloseAttempts		OBJECT-TYPE
        SYNTAX Counter32
        MAX-ACCESS read-only
        STATUS current
        DESCRIPTION
                "The number of channel close attempts for SIP calls."
	::= { ipUnitySipCallStatistics 10 }

ipUnitySipCallChannelCloseFailuresTotal		OBJECT-TYPE
        SYNTAX Counter32
        MAX-ACCESS read-only
        STATUS current
        DESCRIPTION
                "The total number of channel close failures for SIP calls."
	::= { ipUnitySipCallStatistics 11 }

ipUnitySipCallChannelFreeFailures		OBJECT-TYPE
        SYNTAX Counter32
        MAX-ACCESS read-only
        STATUS current
        DESCRIPTION
                "The number of channel free failures for SIP calls."
	::= { ipUnitySipCallStatistics 12 }

ipUnitySipCallChannelCloseFailures		OBJECT-TYPE
        SYNTAX Counter32
        MAX-ACCESS read-only
        STATUS current
        DESCRIPTION
                "The number of channel close failures for SIP calls."
	::= { ipUnitySipCallStatistics 13 }

ipUnitySipCallChannelATMDisconnectFailures		OBJECT-TYPE
        SYNTAX Counter32
        MAX-ACCESS read-only
        STATUS current
        DESCRIPTION
                "The number of channel ATM disconnect failures for SIP calls."
	::= { ipUnitySipCallStatistics 14 }

ipUnitySipCallVxmlOpenAttempts	OBJECT-TYPE
        SYNTAX Counter32
        MAX-ACCESS read-only
        STATUS current
        DESCRIPTION
                "The number of VXMP open attempts for SIP calls."
	::= { ipUnitySipCallStatistics 15 }

ipUnitySipCallVxmlOpenFailuresTotal		OBJECT-TYPE
        SYNTAX Counter32
        MAX-ACCESS read-only
        STATUS current
        DESCRIPTION
                "The total number of VXML open failures for SIP calls."
	::= { ipUnitySipCallStatistics 16 }

ipUnitySipCallVxmlAllocationFailures		OBJECT-TYPE
        SYNTAX Counter32
        MAX-ACCESS read-only
        STATUS current
        DESCRIPTION
                "The number of VXML allocation failures for SIP calls."
	::= { ipUnitySipCallStatistics 17 }

ipUnitySipCallVxmlOpenFailures		OBJECT-TYPE
        SYNTAX Counter32
        MAX-ACCESS read-only
        STATUS current
        DESCRIPTION
                "The number of VXML open failures for SIP calls."
	::= { ipUnitySipCallStatistics 18 }

ipUnitySipCallVxmlStatusSuccesses		OBJECT-TYPE
        SYNTAX Counter32
        MAX-ACCESS read-only
        STATUS current
        DESCRIPTION
                "The number of SIP calls with VXML status success."
	::= { ipUnitySipCallStatistics 19 }

ipUnitySipCallVxmlStatusFailures		OBJECT-TYPE
        SYNTAX Counter32
        MAX-ACCESS read-only
        STATUS current
        DESCRIPTION
                "The number of SIP calls with VXML status failure."
	::= { ipUnitySipCallStatistics 20 }

ipUnitySipCallVxmlCloseAttempts		OBJECT-TYPE
        SYNTAX Counter32
        MAX-ACCESS read-only
        STATUS current
        DESCRIPTION
                "The number of VXML close attempts for SIP calls."
	::= { ipUnitySipCallStatistics 21 }

ipUnitySipCallVxmlCloseFailuresTotal		OBJECT-TYPE
        SYNTAX Counter32
        MAX-ACCESS read-only
        STATUS current
        DESCRIPTION
                "The total number of SIP calls with VXML close failures."
	::= { ipUnitySipCallStatistics 22 }

ipUnitySipCallVxmlCloseFailures		OBJECT-TYPE
        SYNTAX Counter32
        MAX-ACCESS read-only
        STATUS current
        DESCRIPTION
                "The number of SIP calls with VXML close failures."
	::= { ipUnitySipCallStatistics 23 }

ipUnitySipCallVxmlFreeFailures		OBJECT-TYPE
        SYNTAX Counter32
        MAX-ACCESS read-only
        STATUS current
        DESCRIPTION
                "The number of SIP calls with VXML free failures."
	::= { ipUnitySipCallStatistics 24 }

ipUnitySipCallASRRequests		OBJECT-TYPE
        SYNTAX Counter32
        MAX-ACCESS read-only
        STATUS current
        DESCRIPTION
                "The number of SIP calls with ASR requests."
	::= { ipUnitySipCallStatistics 25 }

ipUnitySipCallASRAllocationFailures		OBJECT-TYPE
        SYNTAX Counter32
        MAX-ACCESS read-only
        STATUS current
        DESCRIPTION
                "The number of SIP calls with ASR allocation failures."
	::= { ipUnitySipCallStatistics 26 }

ipUnitySipCallASRATMConnectionFailures		OBJECT-TYPE
        SYNTAX Counter32
        MAX-ACCESS read-only
        STATUS current
        DESCRIPTION
                "The number of SIP calls with ASR ATM connection failures."
	::= { ipUnitySipCallStatistics 27 }

ipUnitySipCallASRATMDisconnectFailures		OBJECT-TYPE
        SYNTAX Counter32
        MAX-ACCESS read-only
        STATUS current
        DESCRIPTION
                "The number of SIP calls with ASR ATM disconnect failures."
	::= { ipUnitySipCallStatistics 28 }

ipUnitySipCallASRFreeFailures		OBJECT-TYPE
        SYNTAX Counter32
        MAX-ACCESS read-only
        STATUS current
        DESCRIPTION
                "The number of SIP calls with ASR free failures."
	::= { ipUnitySipCallStatistics 29 }                            


--Error statistics

ipUnityNumCallG729		OBJECT-TYPE
        SYNTAX Counter32
        MAX-ACCESS read-only
        STATUS current
        DESCRIPTION
                "The total number of G.729 calls"
	::= { ipUnityErrorStatistics 1 }

ipUnityNumCallG723      OBJECT-TYPE
        SYNTAX Counter32
        MAX-ACCESS read-only
        STATUS current
        DESCRIPTION
                "The number of G.723 calls."
	::= {ipUnityErrorStatistics 2 }

ipUnityNumCFCallblock   OBJECT-TYPE
        SYNTAX Counter32
        MAX-ACCESS read-only
        STATUS current
        DESCRIPTION
                "The total number of CF calls that were rejected due to non avaiability of CF resource."
	::= { ipUnityErrorStatistics 3 }

ipUnityNumIVRChannelBlock OBJECT-TYPE
        SYNTAX Counter32
        MAX-ACCESS read-only
        STATUS current
        DESCRIPTION
                "The number of IVR calls that were rejected due to non availability of IVR resource."
	::= { ipUnityErrorStatistics 4 }

ipUnityNumVXMLChannelBlock OBJECT-TYPE
        SYNTAX Counter32
        MAX-ACCESS read-only
        STATUS current
        DESCRIPTION
                "The number of VXML calls that were rejected due to non availability of IVR resource."
	::= { ipUnityErrorStatistics 5 }

ipUnityNumCallG711      OBJECT-TYPE
        SYNTAX Counter32
        MAX-ACCESS read-only
        STATUS current
        DESCRIPTION
                "The total number of G.711 calls"
    ::= { ipUnityErrorStatistics 6 }
	
--MEGACO statistics

ipUnityMegacoCmdSuccessRecvs		OBJECT-TYPE
        SYNTAX Counter32
        MAX-ACCESS read-only
        STATUS current
        DESCRIPTION
                "The total number of Megaco commands received successfully."
	::= { ipUnityMegacoStatistics 1 }

ipUnityMegacoCmdSuccessSends            OBJECT-TYPE
        SYNTAX Counter32
        MAX-ACCESS read-only
        STATUS current
        DESCRIPTION
                "The total number of Megaco commands sent successfully."
	::= { ipUnityMegacoStatistics 2 }

ipUnityMegacoCmdRcvdAdd            OBJECT-TYPE
        SYNTAX Counter32
        MAX-ACCESS read-only
        STATUS current
        DESCRIPTION
                "The total number of Megaco commands received add."
	::= { ipUnityMegacoStatistics 3 }

ipUnityMegacoCmdRcvdSubtract            OBJECT-TYPE
        SYNTAX Counter32
        MAX-ACCESS read-only
        STATUS current
        DESCRIPTION
                "The total number of Megaco commands received subtract."
	::= { ipUnityMegacoStatistics 4 }

ipUnityMegacoCmdRcvdModify            OBJECT-TYPE
        SYNTAX Counter32
        MAX-ACCESS read-only
        STATUS current
        DESCRIPTION
                "The total number of Megaco commands received modify."
	::= { ipUnityMegacoStatistics 5 }

ipUnityMegacoCmdRcvdMove            OBJECT-TYPE
        SYNTAX Counter32
        MAX-ACCESS read-only
        STATUS current
        DESCRIPTION
                "The total number of Megaco commands received move."
	::= { ipUnityMegacoStatistics 6 }

ipUnityMegacoCmdRcvdAuditCap            OBJECT-TYPE
        SYNTAX Counter32
        MAX-ACCESS read-only
        STATUS current
        DESCRIPTION
                "The total number of Megaco commands received audit cap."
	::= { ipUnityMegacoStatistics 7 }

ipUnityMegacoCmdRcvdAuditValue            OBJECT-TYPE
        SYNTAX Counter32
        MAX-ACCESS read-only
        STATUS current
        DESCRIPTION
                "The total number of Megaco commands received audit value."
	::= { ipUnityMegacoStatistics 8 }

ipUnityMegacoCmdRcvdSvcChng            OBJECT-TYPE
        SYNTAX Counter32
        MAX-ACCESS read-only
        STATUS current
        DESCRIPTION
                "The total number of Megaco commands received service change."
	::= { ipUnityMegacoStatistics 9 }

ipUnityMegacoCmdRcvdReplyNotify            OBJECT-TYPE
        SYNTAX Counter32
        MAX-ACCESS read-only
        STATUS current
        DESCRIPTION
                "The total number of Megaco commands received reply notify."
	::= { ipUnityMegacoStatistics 10 }

ipUnityMegacoCmdRcvdReplySvcChng            OBJECT-TYPE
        SYNTAX Counter32
        MAX-ACCESS read-only
        STATUS current
        DESCRIPTION
                "The total number of Megaco commands received reply service change."
	::= { ipUnityMegacoStatistics 11 }

ipUnityMegacoCmdRcvdErrorNotify            OBJECT-TYPE
        SYNTAX Counter32
        MAX-ACCESS read-only
        STATUS current
        DESCRIPTION
                "The total number of Megaco commands received error notify."
	::= { ipUnityMegacoStatistics 12 }

ipUnityMegacoCmdRcvdErrorSvcChng            OBJECT-TYPE
        SYNTAX Counter32
        MAX-ACCESS read-only
        STATUS current
        DESCRIPTION
                "The total number of Megaco commands received error service change."
	::= { ipUnityMegacoStatistics 13 }

ipUnityMegacoCmdSentNotify            OBJECT-TYPE
        SYNTAX Counter32
        MAX-ACCESS read-only
        STATUS current
        DESCRIPTION
                "The total number of Megaco commands sent notify."
	::= { ipUnityMegacoStatistics 14 }

ipUnityMegacoCmdSentSvcChng            OBJECT-TYPE
        SYNTAX Counter32
        MAX-ACCESS read-only
        STATUS current
        DESCRIPTION
                "The total number of Megaco commands sent service change."
	::= { ipUnityMegacoStatistics 15 }

ipUnityMegacoCmdSentReplyAdd            OBJECT-TYPE
        SYNTAX Counter32
        MAX-ACCESS read-only
        STATUS current
        DESCRIPTION
                "The total number of Megaco commands sent reply add."
	::= { ipUnityMegacoStatistics 16 }

ipUnityMegacoCmdSentReplySubtract            OBJECT-TYPE
        SYNTAX Counter32
        MAX-ACCESS read-only
        STATUS current
        DESCRIPTION
                "The total number of Megaco commands sent reply subtract."
	::= { ipUnityMegacoStatistics 17 }

ipUnityMegacoCmdSentReplyModify            OBJECT-TYPE
        SYNTAX Counter32
        MAX-ACCESS read-only
        STATUS current
        DESCRIPTION
                "The total number of Megaco commands sent reply modify."
	::= { ipUnityMegacoStatistics 18 }

ipUnityMegacoCmdSentReplyMove            OBJECT-TYPE
        SYNTAX Counter32
        MAX-ACCESS read-only
        STATUS current
        DESCRIPTION
                "The total number of Megaco commands sent reply move."
	::= { ipUnityMegacoStatistics 19 }

ipUnityMegacoCmdSentReplyAuditCap            OBJECT-TYPE
        SYNTAX Counter32
        MAX-ACCESS read-only
        STATUS current
        DESCRIPTION
                "The total number of Megaco commands sent reply audit cap."
	::= { ipUnityMegacoStatistics 20 }

ipUnityMegacoCmdSentReplyAuditValue            OBJECT-TYPE
        SYNTAX Counter32
        MAX-ACCESS read-only
        STATUS current
        DESCRIPTION
                "The total number of Megaco commands sent reply audit value."
	::= { ipUnityMegacoStatistics 21 }

ipUnityMegacoCmdSentReplySvcChng            OBJECT-TYPE
        SYNTAX Counter32
        MAX-ACCESS read-only
        STATUS current
        DESCRIPTION
                "The total number of Megaco commands sent reply service change."
	::= { ipUnityMegacoStatistics 22 }

ipUnityMegacoCmdSentErrorAdd            OBJECT-TYPE
        SYNTAX Counter32
        MAX-ACCESS read-only
        STATUS current
        DESCRIPTION
                "The total number of Megaco commands sent error add."
	::= { ipUnityMegacoStatistics 23 }

ipUnityMegacoCmdSentErrorSubtract            OBJECT-TYPE
        SYNTAX Counter32
        MAX-ACCESS read-only
        STATUS current
        DESCRIPTION
                "The total number of Megaco commands sent error subtract."
	::= { ipUnityMegacoStatistics 24 }

ipUnityMegacoCmdSentErrorModify            OBJECT-TYPE
        SYNTAX Counter32
        MAX-ACCESS read-only
        STATUS current
        DESCRIPTION
                "The total number of Megaco commands sent error modify."
	::= { ipUnityMegacoStatistics 25 }

ipUnityMegacoCmdSentErrorMove            OBJECT-TYPE
        SYNTAX Counter32
        MAX-ACCESS read-only
        STATUS current
        DESCRIPTION
                "The total number of Megaco commands sent error move."
	::= { ipUnityMegacoStatistics 26 }

ipUnityMegacoCmdSentErrorAuditCap            OBJECT-TYPE
        SYNTAX Counter32
        MAX-ACCESS read-only
        STATUS current
        DESCRIPTION
                "The total number of Megaco commands sent error audit cap."
	::= { ipUnityMegacoStatistics 27 }

ipUnityMegacoCmdSentErrorAuditValue            OBJECT-TYPE
        SYNTAX Counter32
        MAX-ACCESS read-only
        STATUS current
        DESCRIPTION
                "The total number of Megaco commands sent error audit value."
	::= { ipUnityMegacoStatistics 28 }

ipUnityMegacoCmdSentErrorSvcChng            OBJECT-TYPE
        SYNTAX Counter32
        MAX-ACCESS read-only
        STATUS current
        DESCRIPTION
                "The total number of Megaco commands sent error service change."
	::= { ipUnityMegacoStatistics 29 }

ipUnityMegacoErrorResponds            OBJECT-TYPE
        SYNTAX Counter32
        MAX-ACCESS read-only
        STATUS current
        DESCRIPTION
                "The total number of Megaco error responds."
	::= { ipUnityMegacoStatistics 30 }

ipUnityMegacoSuccessResponds            OBJECT-TYPE
        SYNTAX Counter32
        MAX-ACCESS read-only
        STATUS current
        DESCRIPTION
                "The total number of Megaco success responds."
	::= { ipUnityMegacoStatistics 31 }

-- MEGACO Call statistics

ipUnityMegacoNumCallSetupAttempts	OBJECT-TYPE
        SYNTAX Counter32
        MAX-ACCESS read-only
        STATUS current
        DESCRIPTION
                "The number of Call Setup attempts made."
        ::= { ipUnityMegacoCallStatistics 1 }

ipUnityMegacoNumCallSetupFailures	OBJECT-TYPE
        SYNTAX Counter32
        MAX-ACCESS read-only
        STATUS current
        DESCRIPTION
                "The number of Call Setup attempts which failed."
        ::= { ipUnityMegacoCallStatistics 2 }

ipUnityMegacoNumRscAllocFailures	OBJECT-TYPE
        SYNTAX Counter32
        MAX-ACCESS read-only
        STATUS current
        DESCRIPTION
                "The number of Resource Allocation attempts which failed."
        ::= { ipUnityMegacoCallStatistics 3 }

ipUnityMegacoNumChanOpenFailures	OBJECT-TYPE
        SYNTAX Counter32
        MAX-ACCESS read-only
        STATUS current
        DESCRIPTION
                "The number of Channel Open attempts which failed."
        ::= { ipUnityMegacoCallStatistics 4 }

ipUnityMegacoNumATMConnFailures	OBJECT-TYPE
        SYNTAX Counter32
        MAX-ACCESS read-only
        STATUS current
        DESCRIPTION
                "The number of ATM Connection attempts which failed."
        ::= { ipUnityMegacoCallStatistics 5 }

ipUnityMegacoNumCallTearDownAttempts	OBJECT-TYPE
        SYNTAX Counter32
        MAX-ACCESS read-only
        STATUS current
        DESCRIPTION
                "The number of Call TearDown attempts made."
        ::= { ipUnityMegacoCallStatistics 6 }

ipUnityMegacoNumCallTearDownFailures	OBJECT-TYPE
        SYNTAX Counter32
        MAX-ACCESS read-only
        STATUS current
        DESCRIPTION
                "The number of Call TearDown attempts which failed."
        ::= { ipUnityMegacoCallStatistics 7 }

ipUnityMegacoNumRscFreeFailures	OBJECT-TYPE
        SYNTAX Counter32
        MAX-ACCESS read-only
        STATUS current
        DESCRIPTION
                "The number of Resource Freeing attempts which failed."
        ::= { ipUnityMegacoCallStatistics 8 }

ipUnityMegacoNumChanCloseFailures	OBJECT-TYPE
        SYNTAX Counter32
        MAX-ACCESS read-only
        STATUS current
        DESCRIPTION
                "The number of Channel Close attempts which failed."
        ::= { ipUnityMegacoCallStatistics 9 }

ipUnityMegacoNumATMDiscFailures	OBJECT-TYPE
        SYNTAX Counter32
        MAX-ACCESS read-only
        STATUS current
        DESCRIPTION
                "The number of ATM Disconnect attempts which failed."
        ::= { ipUnityMegacoCallStatistics 10 }

ipUnityMegacoNumServiceRequestAttempts	OBJECT-TYPE
        SYNTAX Counter32
        MAX-ACCESS read-only
        STATUS current
        DESCRIPTION
                "The number of service requests attempts made."
        ::= { ipUnityMegacoCallStatistics 11 }

ipUnityMegacoNumServiceRequestFailures	OBJECT-TYPE
        SYNTAX Counter32
        MAX-ACCESS read-only
        STATUS current
        DESCRIPTION
                "The number of service requests attempts which failed."
        ::= { ipUnityMegacoCallStatistics 12 }

ipUnityMegacoNumAsrRequested		OBJECT-TYPE
        SYNTAX Counter32
        MAX-ACCESS read-only
        STATUS current
        DESCRIPTION
                "The number of ASR requests."
        ::= { ipUnityMegacoCallStatistics 13 }

ipUnityMegacoNumAsrAllocationFailure	OBJECT-TYPE
        SYNTAX Counter32
        MAX-ACCESS read-only
        STATUS current
        DESCRIPTION
                "The number of ASR allocation failures."
        ::= { ipUnityMegacoCallStatistics 14 }

ipUnityMegacoNumAsrATMConnectionFailure	OBJECT-TYPE
        SYNTAX Counter32
        MAX-ACCESS read-only
        STATUS current
        DESCRIPTION
                "The number of ASR ATM connection failures."
        ::= { ipUnityMegacoCallStatistics 15 }

ipUnityMegacoNumAsrATMDisconnectFailure	OBJECT-TYPE
        SYNTAX Counter32
        MAX-ACCESS read-only
        STATUS current
        DESCRIPTION
                "The number of ASR ATM disconnect failures."
        ::= { ipUnityMegacoCallStatistics 16 }

ipUnityMegacoNumAsrFreeFailure	OBJECT-TYPE
        SYNTAX Counter32
        MAX-ACCESS read-only
        STATUS current
        DESCRIPTION
                "The number of ASR free failures."
        ::= { ipUnityMegacoCallStatistics 17 }

-- VIDEO statistics

ipUnityVideoNumOfVideoMail	OBJECT-TYPE
        SYNTAX Counter32
        MAX-ACCESS read-only
        STATUS current
        DESCRIPTION
                "The number of video mail."
        ::= { ipUnityVideoStatistics 1 }

ipUnityVideoNumOfVideoConference	OBJECT-TYPE
        SYNTAX Counter32
        MAX-ACCESS read-only
        STATUS current
        DESCRIPTION
                "The number of video conference."
        ::= { ipUnityVideoStatistics 2 }

ipUnityVideoNumOfVideoNway	OBJECT-TYPE
        SYNTAX Counter32
        MAX-ACCESS read-only
        STATUS current
        DESCRIPTION
                "The number of video N way."
        ::= { ipUnityVideoStatistics 3 }

ipUnityVideoNumOfVideoPtoPMake	OBJECT-TYPE
        SYNTAX Counter32
        MAX-ACCESS read-only
        STATUS current
        DESCRIPTION
                "The number of video P to P made."
        ::= { ipUnityVideoStatistics 4 }

ipUnityVideoNumOfVideoPtoPClose	OBJECT-TYPE
        SYNTAX Counter32
        MAX-ACCESS read-only
        STATUS current
        DESCRIPTION
                "The number of video P to P close."
        ::= { ipUnityVideoStatistics 5 }

ipUnityVideoNumOfVideoLoopMake	OBJECT-TYPE
        SYNTAX Counter32
        MAX-ACCESS read-only
        STATUS current
        DESCRIPTION
                "The number of video loop made."
        ::= { ipUnityVideoStatistics 6 }

ipUnityVideoNumOfVideoLoopClose	OBJECT-TYPE
        SYNTAX Counter32
        MAX-ACCESS read-only
        STATUS current
        DESCRIPTION
                "The number of video loop closed."
        ::= { ipUnityVideoStatistics 7 }

ipUnityVideoNumOfVideoConfSwapLoop	OBJECT-TYPE
        SYNTAX Counter32
        MAX-ACCESS read-only
        STATUS current
        DESCRIPTION
                "The number of video conference swap loop."
        ::= { ipUnityVideoStatistics 8 }

ipUnityVideoNumOfVideoMulticastMake	OBJECT-TYPE
        SYNTAX Counter32
        MAX-ACCESS read-only
        STATUS current
        DESCRIPTION
                "The number of video multicast make."
        ::= { ipUnityVideoStatistics 9 }

ipUnityVideoNumOfVideoMulticastClose	OBJECT-TYPE
        SYNTAX Counter32
        MAX-ACCESS read-only
        STATUS current
        DESCRIPTION
                "The number of video multicast closed."
        ::= { ipUnityVideoStatistics 10 }

ipUnityVideoNumOfVideoHairpinAttempt	OBJECT-TYPE
        SYNTAX Counter32
        MAX-ACCESS read-only
        STATUS current
        DESCRIPTION
                "The number of video hairpin attempted."
        ::= { ipUnityVideoStatistics 11 }

ipUnityVideoNumOfVideoHairpinSuccess	OBJECT-TYPE
        SYNTAX Counter32
        MAX-ACCESS read-only
        STATUS current
        DESCRIPTION
                "The number of video hairpin success." 
        ::= { ipUnityVideoStatistics 12 }

ipUnityVideoNumOfVideoHairpinClose	OBJECT-TYPE
        SYNTAX Counter32
        MAX-ACCESS read-only
        STATUS current
        DESCRIPTION
                "The number of video hairpin closed." 
        ::= { ipUnityVideoStatistics 13 }

ipUnityVideoNumOfVideoConfConnMake	OBJECT-TYPE
        SYNTAX Counter32
        MAX-ACCESS read-only
        STATUS current
        DESCRIPTION
                "The number of video conference connection made."
        ::= { ipUnityVideoStatistics 14 }

ipUnityVideoNumOfVideoConfConnClose	OBJECT-TYPE
        SYNTAX Counter32
        MAX-ACCESS read-only
        STATUS current
        DESCRIPTION
                "The number of video conference connection closed." 
        ::= { ipUnityVideoStatistics 15 }

ipUnityVideoNumOfVideoConfChanAllocate	OBJECT-TYPE
        SYNTAX Counter32
        MAX-ACCESS read-only
        STATUS current
        DESCRIPTION
                "The number of video conference channel allocated."
        ::= { ipUnityVideoStatistics 16 }

ipUnityVideoNumOfVideoConfChanAllocateFailure	OBJECT-TYPE
        SYNTAX Counter32
        MAX-ACCESS read-only
        STATUS current
        DESCRIPTION
                "The number of video conference channel failed to allocate." 
        ::= { ipUnityVideoStatistics 17 }

ipUnityVideoNumOfVideoConfChanOpenAttempt	OBJECT-TYPE
        SYNTAX Counter32
        MAX-ACCESS read-only
        STATUS current
        DESCRIPTION
                "The number of video conference channel open attemped."
        ::= { ipUnityVideoStatistics 18 }

ipUnityVideoNumOfVideoConfChanOpenSuccess	OBJECT-TYPE
        SYNTAX Counter32
        MAX-ACCESS read-only
        STATUS current
        DESCRIPTION
                "The number of video conference channel opened successfully."
        ::= { ipUnityVideoStatistics 19 }

ipUnityVideoNumOfVideoConfChanCloseAttempt	OBJECT-TYPE
        SYNTAX Counter32
        MAX-ACCESS read-only
        STATUS current
        DESCRIPTION
                "The number of video conference channel close attempted."
        ::= { ipUnityVideoStatistics 20 }

ipUnityVideoNumOfVideoConfChanCloseSuccess	OBJECT-TYPE
        SYNTAX Counter32
        MAX-ACCESS read-only
        STATUS current
        DESCRIPTION
                "The number of video conference channel closed successfully."
        ::= { ipUnityVideoStatistics 21 }

ipUnityVideoNumOfVideoConfChanVasUpdate	OBJECT-TYPE
        SYNTAX Counter32
        MAX-ACCESS read-only
        STATUS current
        DESCRIPTION
                "The number of video conference channel vas update."
        ::= { ipUnityVideoStatistics 22 }

ipUnityVideoNumOfVideoTranscodeConnMake	OBJECT-TYPE
        SYNTAX Counter32
        MAX-ACCESS read-only
        STATUS current
        DESCRIPTION
                "The number of video transcode connection made."
        ::= { ipUnityVideoStatistics 23 }

ipUnityVideoNumOfVideoTranscodeConnClose	OBJECT-TYPE
        SYNTAX Counter32
        MAX-ACCESS read-only
        STATUS current
        DESCRIPTION
                "The number of video transcode connection closed."
        ::= { ipUnityVideoStatistics 24 }

ipUnityVideoNumOfVideoPlayRecordConnMake	OBJECT-TYPE
        SYNTAX Counter32
        MAX-ACCESS read-only
        STATUS current
        DESCRIPTION
                "The number of video play record connection made."
        ::= { ipUnityVideoStatistics 25 }

ipUnityVideoNumOfVideoPlayRecordConnClose	OBJECT-TYPE
        SYNTAX Counter32
        MAX-ACCESS read-only
        STATUS current
        DESCRIPTION
                "The number of play record conection closed."
        ::= { ipUnityVideoStatistics 26 }

-- TTS Statistics

ipUnityTtsUtilization		OBJECT-TYPE
        SYNTAX INTEGER (0..100)
        MAX-ACCESS read-only
        STATUS current
        DESCRIPTION
                "The percentage utilization of the TTS engine."
	::= { ipUnityTTSStatistics 1 }

ipUnityTtsAllocateAttempts	OBJECT-TYPE
	SYNTAX	Counter32
      MAX-ACCESS read-only
      STATUS current
      DESCRIPTION
                "The number of TTS allocate attempts."
    ::= { ipUnityTTSStatistics 2 }

ipUnityTtsAllocateSuccesses	OBJECT-TYPE
	SYNTAX	Counter32
     	MAX-ACCESS read-only
      STATUS current
      DESCRIPTION
                "The number of TTS allocate successes."
    ::= { ipUnityTTSStatistics 3 }

ipUnityTtsAllocateFailures	OBJECT-TYPE
	SYNTAX	Counter32
      MAX-ACCESS read-only
      STATUS current
      DESCRIPTION
                "The number of TTS allocate failures."
    ::= { ipUnityTTSStatistics 4 }

ipUnityTtsActiveAttempts	OBJECT-TYPE
	SYNTAX	Counter32
      MAX-ACCESS read-only
      STATUS current
      DESCRIPTION
                "The number of TTS active attempts."
    ::= { ipUnityTTSStatistics 5 }

ipUnityTtsActiveSuccesses	OBJECT-TYPE
	SYNTAX	Counter32
     	MAX-ACCESS read-only
      STATUS current
      DESCRIPTION
                "The number of TTS active successes."
    ::= { ipUnityTTSStatistics 6 }

ipUnityTtsActiveFailures	OBJECT-TYPE
	SYNTAX	Counter32
      MAX-ACCESS read-only
      STATUS current
      DESCRIPTION
                "The number of TTS active failures."
    ::= { ipUnityTTSStatistics 7 }

ipUnityTtsSynthesizeAttempts	OBJECT-TYPE
	SYNTAX	Counter32
      MAX-ACCESS read-only
      STATUS current
      DESCRIPTION
                "The number of TTS synthesize attempts."
    ::= { ipUnityTTSStatistics 8 }

ipUnityTtsSynthesizeSuccesses	OBJECT-TYPE
	SYNTAX	Counter32
     	MAX-ACCESS read-only
      STATUS current
      DESCRIPTION
                "The number of TTS synthesize successes."
    ::= { ipUnityTTSStatistics 9 }

ipUnityTtsSynthesizeStops	OBJECT-TYPE
	SYNTAX	Counter32
      MAX-ACCESS read-only
      STATUS current
      DESCRIPTION
                "The number of TTS synthesize stops."
    ::= { ipUnityTTSStatistics 10 }

ipUnityTtsSynthesizeRejections	OBJECT-TYPE
	SYNTAX	Counter32
      MAX-ACCESS read-only
      STATUS current
      DESCRIPTION
                "The number of TTS synthesize rejections."
    ::= { ipUnityTTSStatistics 11 }

--MSML statistics

msmlCtrlRtpChannelOpen		OBJECT-TYPE
        SYNTAX Counter32
        MAX-ACCESS read-only
        STATUS current
        DESCRIPTION
                "The number of MSML Control RTP Channel Open."
	::= { msmlCallStatistics 1 }

msmlCtrlChannelOpen            OBJECT-TYPE
        SYNTAX Counter32
        MAX-ACCESS read-only
        STATUS current
        DESCRIPTION
                "The number of MSML Ctrl Channel Open."
	::= { msmlCallStatistics 2 }

msmlAudioIVROpen		OBJECT-TYPE
        SYNTAX Counter32
        MAX-ACCESS read-only
        STATUS current
        DESCRIPTION
                "The number of MSML Audio IVR Open."
	::= { msmlCallStatistics 3 }

msmlVideoIVROpen            OBJECT-TYPE
        SYNTAX Counter32
        MAX-ACCESS read-only
        STATUS current
        DESCRIPTION
                "The number of MSML Video IVR Open."
	::= { msmlCallStatistics 4 }

msmlAudioCnfOpen		OBJECT-TYPE
        SYNTAX Counter32
        MAX-ACCESS read-only
        STATUS current
        DESCRIPTION
                "The number of MSML Audio Conference Open."
	::= { msmlCallStatistics 5 }

msmlVideoCnfOpen            OBJECT-TYPE
        SYNTAX Counter32
        MAX-ACCESS read-only
        STATUS current
        DESCRIPTION
                "The number of MSML Video Conference Open."
	::= { msmlCallStatistics 6 }

msmlFAXOpen		OBJECT-TYPE
        SYNTAX Counter32
        MAX-ACCESS read-only
        STATUS current
        DESCRIPTION
                "The number of MSML Fax Open."
	::= { msmlCallStatistics 7 }

msmlCtrlRtpChannelClose            OBJECT-TYPE
        SYNTAX Counter32
        MAX-ACCESS read-only
        STATUS current
        DESCRIPTION
                "The number of MSML Control RTP Channel Close."
	::= { msmlCallStatistics 8 }

msmlCtrlChannelClose            OBJECT-TYPE
        SYNTAX Counter32
        MAX-ACCESS read-only
        STATUS current
        DESCRIPTION
                "The number of MSML Control Channel Close."
	::= { msmlCallStatistics 9 }

msmlAudioIVRClose		OBJECT-TYPE
        SYNTAX Counter32
        MAX-ACCESS read-only
        STATUS current
        DESCRIPTION
                "The number of MSML Audio IVR Close."
	::= { msmlCallStatistics 10 }

msmlVideoIVRClose            OBJECT-TYPE
        SYNTAX Counter32
        MAX-ACCESS read-only
        STATUS current
        DESCRIPTION
                "The number of Msml Video IVR Close."
	::= { msmlCallStatistics 11 }

msmlAudioCnfClose		OBJECT-TYPE
        SYNTAX Counter32
        MAX-ACCESS read-only
        STATUS current
        DESCRIPTION
                "The number of MSML Audio Conference Close."
	::= { msmlCallStatistics 12 }

msmlVideoCnfClose            OBJECT-TYPE
        SYNTAX Counter32
        MAX-ACCESS read-only
        STATUS current
        DESCRIPTION
                "The number of MSML Video Conference Close."
	::= { msmlCallStatistics 13 }

msmlFAXClose		OBJECT-TYPE
        SYNTAX Counter32
        MAX-ACCESS read-only
        STATUS current
        DESCRIPTION
                "The number of MSML Fax Close."
	::= { msmlCallStatistics 14 }

-- MSML Conference Statistics

msmlCnfCreatjoin		OBJECT-TYPE
        SYNTAX Counter32
        MAX-ACCESS read-only
        STATUS current
        DESCRIPTION
                "The number of MSML Conference Create join."
	::= { msmlConfStatistics 1 }

msmlCnfCreatjoinOk            OBJECT-TYPE
        SYNTAX Counter32
        MAX-ACCESS read-only
        STATUS current
        DESCRIPTION
                "The number of MSML Conference Create join ok."
	::= { msmlConfStatistics 2 }

msmlCnfCreatjoinError		OBJECT-TYPE
        SYNTAX Counter32
        MAX-ACCESS read-only
        STATUS current
        DESCRIPTION
                "The number of MSML Conference Create join error."
	::= { msmlConfStatistics 3 }

msmlCnfCreat            OBJECT-TYPE
        SYNTAX Counter32
        MAX-ACCESS read-only
        STATUS current
        DESCRIPTION
                "The number of MSML Conference Create."
	::= { msmlConfStatistics 4 }

msmlCnfCreatOk		OBJECT-TYPE
        SYNTAX Counter32
        MAX-ACCESS read-only
        STATUS current
        DESCRIPTION
                "The number of MSML Conference Create Ok."
	::= { msmlConfStatistics 5 }

msmlCnfCreatError            OBJECT-TYPE
        SYNTAX Counter32
        MAX-ACCESS read-only
        STATUS current
        DESCRIPTION
                "The number of MSML Conference Create error."
	::= { msmlConfStatistics 6 }

msmlCnfModify		OBJECT-TYPE
        SYNTAX Counter32
        MAX-ACCESS read-only
        STATUS current
        DESCRIPTION
                "The number of MSML Conference modify."
	::= { msmlConfStatistics 7 }

msmlCnfModifyOk            OBJECT-TYPE
        SYNTAX Counter32
        MAX-ACCESS read-only
        STATUS current
        DESCRIPTION
                "The number of MSML Conference modify ok."
	::= { msmlConfStatistics 8 }

msmlCnfModifyError		OBJECT-TYPE
        SYNTAX Counter32
        MAX-ACCESS read-only
        STATUS current
        DESCRIPTION
                "The number of MSML Conference modify error."
	::= { msmlConfStatistics 9 }

msmlCnfDestroy            OBJECT-TYPE
        SYNTAX Counter32
        MAX-ACCESS read-only
        STATUS current
        DESCRIPTION
                "The number of MSML Conference destroy."
	::= { msmlConfStatistics 10 }

msmlCnfDestroyOk		OBJECT-TYPE
        SYNTAX Counter32
        MAX-ACCESS read-only
        STATUS current
        DESCRIPTION
                "The number of MSML Conference destroy ok."
	::= { msmlConfStatistics 11 }

msmlCnfDestroyError            OBJECT-TYPE
        SYNTAX Counter32
        MAX-ACCESS read-only
        STATUS current
        DESCRIPTION
                "The number of MSML Conference destroy error."
	::= { msmlConfStatistics 12 }

msmlCnfEnd		OBJECT-TYPE
        SYNTAX Counter32
        MAX-ACCESS read-only
        STATUS current
        DESCRIPTION
                "The number of MSML Conference end."
	::= { msmlConfStatistics 13 }

msmlCnfEndOk            OBJECT-TYPE
        SYNTAX Counter32
        MAX-ACCESS read-only
        STATUS current
        DESCRIPTION
                "The number of MSML Conference end ok."
	::= { msmlConfStatistics 14 }

msmlCnfEndError		OBJECT-TYPE
        SYNTAX Counter32
        MAX-ACCESS read-only
        STATUS current
        DESCRIPTION
                "The number of MSML Conference end error."
	::= { msmlConfStatistics 15 }

msmlCnfJoin            OBJECT-TYPE
        SYNTAX Counter32
        MAX-ACCESS read-only
        STATUS current
        DESCRIPTION
                "The number of MSML Conference join."
	::= { msmlConfStatistics 16 }

msmlCnfJoinOk		OBJECT-TYPE
        SYNTAX Counter32
        MAX-ACCESS read-only
        STATUS current
        DESCRIPTION
                "The number of MSML Conference join ok."
	::= { msmlConfStatistics 17 }

msmlCnfJoinError            OBJECT-TYPE
        SYNTAX Counter32
        MAX-ACCESS read-only
        STATUS current
        DESCRIPTION
                "The number of MSML Conference join error."
	::= { msmlConfStatistics 18 }

msmlCnfUnjoin		OBJECT-TYPE
        SYNTAX Counter32
        MAX-ACCESS read-only
        STATUS current
        DESCRIPTION
                "The number of MSML Conference unjoin."
	::= { msmlConfStatistics 19 }

msmlCnfUnjoinOk            OBJECT-TYPE
        SYNTAX Counter32
        MAX-ACCESS read-only
        STATUS current
        DESCRIPTION
                "The number of MSML Conference unjoin ok."
	::= { msmlConfStatistics 20 }

msmlCnfUnjoinError		OBJECT-TYPE
        SYNTAX Counter32
        MAX-ACCESS read-only
        STATUS current
        DESCRIPTION
                "The number of MSML Conference unjoin error."
	::= { msmlConfStatistics 21 }

msmlStreamModify            OBJECT-TYPE
        SYNTAX Counter32
        MAX-ACCESS read-only
        STATUS current
        DESCRIPTION
                "The number of MSML stream modify."
	::= { msmlConfStatistics 22 }

msmlStreamModifyOk		OBJECT-TYPE
        SYNTAX Counter32
        MAX-ACCESS read-only
        STATUS current
        DESCRIPTION
                "The number of MSML stream modify ok."
	::= { msmlConfStatistics 23 }

msmlStreamModifyError            OBJECT-TYPE
        SYNTAX Counter32
        MAX-ACCESS read-only
        STATUS current
        DESCRIPTION
                "The number of MSML stream modify error."
	::= { msmlConfStatistics 24 }

-- MSML Dialog Statistics

msmlDialogStart            OBJECT-TYPE
        SYNTAX Counter32
        MAX-ACCESS read-only
        STATUS current
        DESCRIPTION
                "The number of MSML Dialog Start."
	::= { msmlDialogStatistics 1 }

msmlDialogStartOk		OBJECT-TYPE
        SYNTAX Counter32
        MAX-ACCESS read-only
        STATUS current
        DESCRIPTION
                "The number of MSML Dialog Start ok."
	::= { msmlDialogStatistics 2 }

msmlDialogStartError            OBJECT-TYPE
        SYNTAX Counter32
        MAX-ACCESS read-only
        STATUS current
        DESCRIPTION
                "The number of MSML Dialog Start error."
	::= { msmlDialogStatistics 3 }

msmlDialogEnd		OBJECT-TYPE
        SYNTAX Counter32
        MAX-ACCESS read-only
        STATUS current
        DESCRIPTION
                "The number of MSML Dialog end."
	::= { msmlDialogStatistics 4 }

msmlDialogEndOk            OBJECT-TYPE
        SYNTAX Counter32
        MAX-ACCESS read-only
        STATUS current
        DESCRIPTION
                "The number of MSML Dialog end ok."
	::= { msmlDialogStatistics 5 }

msmlDialogEndError		OBJECT-TYPE
        SYNTAX Counter32
        MAX-ACCESS read-only
        STATUS current
        DESCRIPTION
                "The number of MSML Dialog end error."
	::= { msmlDialogStatistics 6 }

msmlDialogExit            OBJECT-TYPE
        SYNTAX Counter32
        MAX-ACCESS read-only
        STATUS current
        DESCRIPTION
                "The number of MSML Dialog exit."
	::= { msmlDialogStatistics 7 }

msmlDialogPlay		OBJECT-TYPE
        SYNTAX Counter32
        MAX-ACCESS read-only
        STATUS current
        DESCRIPTION
                "The number of MSML Dialog play."
	::= { msmlDialogStatistics 8 }

msmlDialogPlayOk            OBJECT-TYPE
        SYNTAX Counter32
        MAX-ACCESS read-only
        STATUS current
        DESCRIPTION
                "The number of MSML Dialog play ok."
	::= { msmlDialogStatistics 9 }

msmlDialogPlayError		OBJECT-TYPE
        SYNTAX Counter32
        MAX-ACCESS read-only
        STATUS current
        DESCRIPTION
                "The number of MSML Dialog play error."
	::= { msmlDialogStatistics 10 }

msmlDialogDtmf            OBJECT-TYPE
        SYNTAX Counter32
        MAX-ACCESS read-only
        STATUS current
        DESCRIPTION
                "The number of MSML Dialog dtmf."
	::= { msmlDialogStatistics 11 }

msmlDialogDtmfOk		OBJECT-TYPE
        SYNTAX Counter32
        MAX-ACCESS read-only
        STATUS current
        DESCRIPTION
                "The number of MSML Dialog dtmf ok."
	::= { msmlDialogStatistics 12 }

msmlDialogDtmfError            OBJECT-TYPE
        SYNTAX Counter32
        MAX-ACCESS read-only
        STATUS current
        DESCRIPTION
                "The number of MSML Dialog dtmf error."
	::= { msmlDialogStatistics 13 }

msmlDialogRecord		OBJECT-TYPE
        SYNTAX Counter32
        MAX-ACCESS read-only
        STATUS current
        DESCRIPTION
                "The number of MSML Dialog record."
	::= { msmlDialogStatistics 14 }

msmlDialogRecordOk            OBJECT-TYPE
        SYNTAX Counter32
        MAX-ACCESS read-only
        STATUS current
        DESCRIPTION
                "The number of MSML Dialog record ok."
	::= { msmlDialogStatistics 15 }

msmlDialogRecordError		OBJECT-TYPE
        SYNTAX Counter32
        MAX-ACCESS read-only
        STATUS current
        DESCRIPTION
                "The number of MSML Dialog record error."
	::= { msmlDialogStatistics 16 }

msmlDialogDtmfgen            OBJECT-TYPE
        SYNTAX Counter32
        MAX-ACCESS read-only
        STATUS current
        DESCRIPTION
                "The number of MSML Dialog Dtmf gen."
	::= { msmlDialogStatistics 17 }

msmlDialogDtmfgenOk		OBJECT-TYPE
        SYNTAX Counter32
        MAX-ACCESS read-only
        STATUS current
        DESCRIPTION
                "The number of MSML Dialog Dtmf gen ok."
	::= { msmlDialogStatistics 18 }

msmlDialogDtmfgenError            OBJECT-TYPE
        SYNTAX Counter32
        MAX-ACCESS read-only
        STATUS current
        DESCRIPTION
                "The number of MSML Dialog Dtmf gen error."
	::= { msmlDialogStatistics 19 }

msmlDialogFax            OBJECT-TYPE
        SYNTAX Counter32
        MAX-ACCESS read-only
        STATUS current
        DESCRIPTION
                "The number of MSML Dialog fax."
	::= { msmlDialogStatistics 20 }

msmlDialogFaxOk		OBJECT-TYPE
        SYNTAX Counter32
        MAX-ACCESS read-only
        STATUS current
        DESCRIPTION
                "The number of MSML Dialog fax ok."
	::= { msmlDialogStatistics 21 }

msmlDialogFaxError		OBJECT-TYPE
        SYNTAX Counter32
        MAX-ACCESS read-only
        STATUS current
        DESCRIPTION
                "The number of MSML Dialog fax error."
	::= { msmlDialogStatistics 22 }

-- Media Server Configuration Objects

nodeConfig			OBJECT IDENTIFIER ::= { msConfigurationObjects 1 }
sysConfig			OBJECT IDENTIFIER ::= { msConfigurationObjects 2 }
dnsConfig			OBJECT IDENTIFIER ::= { msConfigurationObjects 3 }
mgcpConfig			OBJECT IDENTIFIER ::= { msConfigurationObjects 4 }
sipConfig			OBJECT IDENTIFIER ::= { msConfigurationObjects 5 }
rtpConfig			OBJECT IDENTIFIER ::= { msConfigurationObjects 6 }
httpConfig			OBJECT IDENTIFIER ::= { msConfigurationObjects 7 }
asrConfig			OBJECT IDENTIFIER ::= { msConfigurationObjects 8 } 
auditTimerConfig	OBJECT IDENTIFIER ::= { msConfigurationObjects 9 }
ipUnityAnncConfig			OBJECT IDENTIFIER ::= { msConfigurationObjects 10 }
esConfig			OBJECT IDENTIFIER ::= { msConfigurationObjects 11 }
fileSystemConfig	OBJECT IDENTIFIER ::= { msConfigurationObjects 12 }
icmAsrConfig		OBJECT IDENTIFIER ::= { msConfigurationObjects 13 }
evConfig			OBJECT IDENTIFIER ::= { msConfigurationObjects 14 }
staticRouteConfig	OBJECT IDENTIFIER ::= { msConfigurationObjects 15 }
netConfig			OBJECT IDENTIFIER ::= { msConfigurationObjects 16 }
sccCpConfig			OBJECT IDENTIFIER ::= { msConfigurationObjects 17 }
spmG4Config			OBJECT IDENTIFIER ::= { msConfigurationObjects 18 }
snmpConfig			OBJECT IDENTIFIER ::= { msConfigurationObjects 19 }
faxConfig			OBJECT IDENTIFIER ::= { msConfigurationObjects 20 }
ipUnityCallPreservConfig   	OBJECT IDENTIFIER ::= { msConfigurationObjects 21 }
ipUnityConfConfig          	OBJECT IDENTIFIER ::= { msConfigurationObjects 22 }
ipUnityEmbeddedVarConfig    OBJECT IDENTIFIER ::= { msConfigurationObjects 23 }
ipUnityH248Config                OBJECT IDENTIFIER ::= { msConfigurationObjects 24 }
ipUnityEndPointConfig           OBJECT IDENTIFIER ::= { msConfigurationObjects 25 }
ipUnityPartitionConfig           OBJECT IDENTIFIER ::= { msConfigurationObjects 26 }
ipUnityVideoImageConfig           OBJECT IDENTIFIER ::= { msConfigurationObjects 27 }
ipUnityIcmConfig		OBJECT IDENTIFIER ::= { msConfigurationObjects 28 }
ipUnityPriorityCallConfig	OBJECT IDENTIFIER ::= { msConfigurationObjects 29 }
dscpConfig               OBJECT IDENTIFIER ::= { msConfigurationObjects 30 } 

-- nodeConfig group contains parameters related to nodeID, hostname, 
-- network etc.,

siteName OBJECT-TYPE
	SYNTAX DisplayString
	MAX-ACCESS read-write
	STATUS current
	DESCRIPTION
		"Location name for Media Server."
	::= { nodeConfig 1 }
	
frameName OBJECT-TYPE
	SYNTAX DisplayString
	MAX-ACCESS read-write
	STATUS current
	DESCRIPTION
		"Frame name for Media Server."
	::= { nodeConfig 2 }	

shelfName OBJECT-TYPE
	SYNTAX DisplayString
	MAX-ACCESS read-write
	STATUS current
	DESCRIPTION
		"Shelf name for Media Server."
	::= { nodeConfig 3 }	
	
nodeName OBJECT-TYPE
	SYNTAX DisplayString
	MAX-ACCESS read-write
	STATUS current
	DESCRIPTION
		"Name for Media Server."
	::= { nodeConfig 4 }	

--signallingHostName0 OBJECT-TYPE
--	SYNTAX DisplayString
--	MAX-ACCESS read-write
--	STATUS obsolete
--	DESCRIPTION
--		"Host name 0 for the signaling interface."
--	::= { nodeConfig 5 }	
--
--signallingHostName1 OBJECT-TYPE
--	SYNTAX DisplayString
--	MAX-ACCESS read-write
--	STATUS current
--	DESCRIPTION
--		"Host name 1 for the signaling interface."
--	::= { nodeConfig 6 }	
--	
--signallingHostName2 OBJECT-TYPE
--	SYNTAX DisplayString
--	MAX-ACCESS read-write
--	STATUS current
--	DESCRIPTION
--		"Host name 2 for the signaling interface."
--	::= { nodeConfig 7 }	
--
--scc1MgmtHostName OBJECT-TYPE
--	SYNTAX DisplayString
--	MAX-ACCESS read-write
--	STATUS current
--	DESCRIPTION
--		"Host name for management interface of scc 1."
--	::= { nodeConfig 8 }	
--
--scc2MgmtHostName OBJECT-TYPE
--	SYNTAX DisplayString
--	MAX-ACCESS read-write
--	STATUS current
--	DESCRIPTION
--		"Host name for management interface of scc 2."
--	::= { nodeConfig 9 }	
--	
--fileSystemHostName OBJECT-TYPE
--	SYNTAX DisplayString
--	MAX-ACCESS read-write
--	STATUS current
--	DESCRIPTION
--		"Host name to use for nfs interface."
--	::= { nodeConfig 10 }	
-- 

ipUnityHostNameTable OBJECT-TYPE
	SYNTAX SEQUENCE OF IpUnityHostNameEntry
	MAX-ACCESS not-accessible
	STATUS current
	DESCRIPTION
		"The table contains hostname configuration info."
	::= { nodeConfig 11 }

ipUnityHostNameEntry  OBJECT-TYPE
	SYNTAX IpUnityHostNameEntry
    MAX-ACCESS not-accessible
    STATUS current
    DESCRIPTION
		"An entry for hostname details."
    INDEX { ipUnityHostNameIndex }
    ::= { ipUnityHostNameTable 1 }

IpUnityHostNameEntry ::= SEQUENCE {
	ipUnityHostNameIndex		Integer32,
	ipUnityHostName  	        DisplayString,
	ipUnityHostNameType		INTEGER,
	ipUnityHostNameRowStatus	RowStatus
	}

ipUnityHostNameIndex	OBJECT-TYPE
	SYNTAX Integer32 (0..5)
	MAX-ACCESS not-accessible
	STATUS current
	DESCRIPTION
		"HostName entry number in the table."
    ::= { ipUnityHostNameEntry 1 }

ipUnityHostName	OBJECT-TYPE
	SYNTAX DisplayString
	MAX-ACCESS read-create
	STATUS current
	DESCRIPTION
		"Host name."
    ::= { ipUnityHostNameEntry 2 }

ipUnityHostNameType	OBJECT-TYPE
	SYNTAX INTEGER {
		signal-media (0),
		mgmt (1),
		nfs (2)
	}
	MAX-ACCESS read-create
	STATUS current
	DESCRIPTION
		"Hostname Type:  signal-media, mgmt or nfs."
    ::= { ipUnityHostNameEntry 3 }    

ipUnityHostNameRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityHostNameEntry 4 }    	
    
-- System configuration objects

cngPayloadType OBJECT-TYPE
	SYNTAX Integer32(13 | 19)
	MAX-ACCESS read-write
	STATUS current
	DESCRIPTION
		""		
	::= { sysConfig 1 }

defaultLanguage OBJECT-TYPE
	SYNTAX Language
	MAX-ACCESS read-write
	STATUS current
	DESCRIPTION
		"Default language."		
	::= { sysConfig 2 }

defaultRecording OBJECT-TYPE
	SYNTAX INTEGER {
		g711 (1),
 		gsm-efr (2),
		gsm-amr (5)
    }
	MAX-ACCESS read-write
	STATUS current
	DESCRIPTION
		"Default recording."		
	::= { sysConfig 3 }

telnetSessionTimer OBJECT-TYPE
	SYNTAX Integer32 (0..2147483647)
	UNITS "minutes" 
	MAX-ACCESS read-write
	STATUS current
	DESCRIPTION
		"Timeout value for a telnet session in minutes."
	DEFVAL {0}		
	::= { sysConfig 4 }
	
rloginSessionTimer OBJECT-TYPE
	SYNTAX Integer32 (0..2147483647)
	UNITS "minutes" 
	MAX-ACCESS read-write
	STATUS current
	DESCRIPTION
		"Timeout value for a rlogin session in minutes."
	DEFVAL {0}		
	::= { sysConfig 5 }

silenceHangoverTime OBJECT-TYPE
	SYNTAX Integer32(0..2000)
	UNITS "milliseconds" 
	MAX-ACCESS read-write
	STATUS current
	DESCRIPTION
		"Silence hangover time."
	DEFVAL {200}		
	::= { sysConfig 6 }				

speechHangoverTime OBJECT-TYPE
	SYNTAX Integer32(0..2000)
	UNITS "milliseconds" 
	MAX-ACCESS read-write
	STATUS current
	DESCRIPTION
		"Speech hangover time."
	DEFVAL {200}		
	::= { sysConfig 7 }				

--mediaTosPrecedence OBJECT-TYPE
--	SYNTAX Integer32(0..5)
--	MAX-ACCESS read-write
--	STATUS obsolete
--	DESCRIPTION
--		"Tos precedence value for media."
--	DEFVAL {5}		
--	::= { sysConfig 8 }	

--signalingTosPrecedence OBJECT-TYPE
--	SYNTAX Integer32(0..5)
--	MAX-ACCESS read-write
--	STATUS obsolete
--	DESCRIPTION
--		"Tos precedence value for signaling."
--	DEFVAL {5}		
--	::= { sysConfig 9 }

systemUtilizationThreshold OBJECT-TYPE
	SYNTAX Integer32(0..100)
	MAX-ACCESS read-write
	STATUS current
	DESCRIPTION
		"Threshold for system utilization."
	::= { sysConfig 10 }
	
bankUtilizationThreshold OBJECT-TYPE
	SYNTAX Integer32(0..100)
	MAX-ACCESS read-write
	STATUS current
	DESCRIPTION
		"Threshold for bank utilization."
	::= { sysConfig 11 }			

languageList OBJECT-TYPE
	SYNTAX OCTET STRING (SIZE (1..3))
	MAX-ACCESS read-write
	STATUS current
	DESCRIPTION
		"List of the languages. one byte for each language. Byte value 
		takes one value from the Language enumeration defined in 
		Textual conventions. User can set one, two or three languages in
		the list. Same language can not be repeated.
		
		Some Excamples or
		  a) English(1), Spanish(3)                 (0x01 0x03)
		  b) Chinese(2), English(1), Spanish(3)     (0x02 0x01 0x03)
		  c) Russian(6)                             (0x06)
		."
	::= { sysConfig 12 }

historyLog	OBJECT-TYPE
	SYNTAX INTEGER {
		off (0),
		on (1)
	}
	MAX-ACCESS read-write
	STATUS current
	DESCRIPTION
		"Turn History Logging off or on."
	DEFVAL	{off}
    ::= { sysConfig 13 }

--- NTP configuration    
ntpPrimaryAddress	OBJECT-TYPE
	SYNTAX DisplayString
	MAX-ACCESS read-write
	STATUS current
	DESCRIPTION
		"Primary NTP Host Name or IP Address"
    ::= { sysConfig 14 }

ntpSecondaryAddress	OBJECT-TYPE
	SYNTAX DisplayString
	MAX-ACCESS read-write
	STATUS current
	DESCRIPTION
		"Secondary NTP Host Name or IP Address"
    ::= { sysConfig 15 }        
    
--- standbyShellAccess configuration
standbyShellAccess	OBJECT-TYPE
	SYNTAX INTEGER {
		off (0),
		on (1)
	}
	MAX-ACCESS read-write
	STATUS current
	DESCRIPTION
		"Turn Standby-Shell Access off or on."
	DEFVAL	{off}
    ::= { sysConfig 16 }

--- Resource configuration
resourceTable OBJECT-TYPE
	SYNTAX SEQUENCE OF ResourceEntry
	MAX-ACCESS not-accessible
	STATUS current
	DESCRIPTION
		"The table contains resource configurations."
	::= { sysConfig 17 }

resourceEntry  OBJECT-TYPE
	SYNTAX ResourceEntry
    MAX-ACCESS not-accessible
    STATUS current
    DESCRIPTION
		"An entry per interface"
    INDEX      { resourceType }
    ::= { resourceTable 1 }

ResourceEntry ::= SEQUENCE {
	resourceType			INTEGER,
	resourceChannel			Integer32
	}
    
resourceType	OBJECT-TYPE
	SYNTAX INTEGER {
		ivr (1),
		cnf (2),
		cnfah (3),
		fax (4),
                es (5),
		video-ivr(6),
		video-conf(7)
	}
	MAX-ACCESS not-accessible
	STATUS current
	DESCRIPTION
		"Resource Type:  ivr, cnf, cnfah, fax, or es."
    ::= { resourceEntry 1 }    

resourceChannel	OBJECT-TYPE
	SYNTAX Integer32(0..2147483647)
	MAX-ACCESS read-write
	STATUS current
	DESCRIPTION
		"The number of channels to be configured for the resource type."
	DEFVAL {0}
    ::= { resourceEntry 2 }
           
--- Statistics Schedule configuration
statisticsSchedule	OBJECT-TYPE
	SYNTAX Integer32(5..30)
	UNITS "Minutes"
	MAX-ACCESS read-write
	STATUS current
	DESCRIPTION
		"Stastics Schedule:  5-30 minutes, initially defaulted to 15 minutes."
	DEFVAL	{15}
    ::= { sysConfig 18 }

--- Time Zone configuration
timeZone	OBJECT-TYPE
        SYNTAX INTEGER	{
			nibt (-23),
			lbt (-22),
			aust (-21),
			cbt (-18),
			ist (-17),
			abt (-16),
			ibt (-15),
			nzst (-12),
			sbt (-11),
			gst (-10),
			jst (-9),
			cct (-8),
			wast (-7),
			bbt (-6),
			pbt (-5),
			mbt (-4),
			bt (-3),
			eet (-2),
			cet (-1),
			gmt (0),
			wat (1),
			at (2),
			gbt (3),
			ast (4),
			est (5),
			cst (6),
			mst (7),
			pst (8),
			yst (9),
			ahstORcatORhst (10),
			nt (11),
			idlw (12),
			nbt (15)
	}
	MAX-ACCESS read-write
	STATUS current
	DESCRIPTION
		"Setting the Time Zone:  initially defaulted to PST."
	DEFVAL	{pst}
    ::= { sysConfig 19 }

configErrStringTable OBJECT-TYPE
	SYNTAX SEQUENCE OF ConfigErrStringEntry
	MAX-ACCESS not-accessible
	STATUS current
	DESCRIPTION
		"The table contains Error information for latest set request."
	::= { sysConfig 20 }

configErrStringEntry  OBJECT-TYPE
	SYNTAX ConfigErrStringEntry
        MAX-ACCESS not-accessible
        STATUS current
        DESCRIPTION
		"An entry per one error string"
        INDEX      { configErrIndex }
        ::= { configErrStringTable 1 }

ConfigErrStringEntry ::= SEQUENCE {
	configErrIndex			Integer32,
	configErrString			DisplayString
	}
    
configErrIndex	OBJECT-TYPE
	SYNTAX Integer32 (0..9)
	MAX-ACCESS not-accessible
        STATUS current
        DESCRIPTION
		"Index for this table. Atmost a set request will have 10 error strings"
        ::= { configErrStringEntry 1 }

configErrString OBJECT-TYPE
	SYNTAX DisplayString
	MAX-ACCESS read-only
	STATUS current
	DESCRIPTION
		"Error string that gives the reason for latest SNMP set failure.  
		When a SNMP Set request fails this string gives the reason
		for its failure.

		For all standard failures like noSuchName, bad value etc 
		management station should depend on error status field
		in the response.
	
		This string is updated for non SNMP standard errors. For
		any reason if error can not be determined by the agent then 
		agent returns null string (0 length).

		This string gives the result of the latest SNMP set request 
		that is handled by the agent. It is management station's 
		responsibility to read the result before performing another 
		SET operation." 
	::= { configErrStringEntry 2 }

	
--- Out of sync Threshold configuration
outOfSyncThreshold	OBJECT-TYPE
	SYNTAX Integer32(0..100)
	MAX-ACCESS read-write
	STATUS current
	DESCRIPTION
		"The threshold value for the sync-audit between Standby and Active SCC."
    ::= { sysConfig 21 }

ipUnitySetBanner       OBJECT-TYPE
    SYNTAX INTEGER {
        off (0),
        on (1)
    }
    MAX-ACCESS read-write
    STATUS current
    DESCRIPTION
        "Enable or disbale the banner."
    ::= { sysConfig 22 }

ipUnityDefaultVedioRecording OBJECT-TYPE
	SYNTAX INTEGER {
		threegp (21)
    }
	MAX-ACCESS read-write
	STATUS current
	DESCRIPTION
		"Storage format for the videomail call."
	::= { sysConfig 23 }

ipUnityGenTrapForOutstandingAlarms OBJECT-TYPE
	SYNTAX INTEGER {
		none(-1),
		informational (2),
	        minor (4),
	        major (5),
	        critical (6),
	        all(10)	
    }
	MAX-ACCESS read-write
	STATUS current
	DESCRIPTION
                "This object allows to generate traps for the outstanding alarms
	based on the severity set. Traps will be sent out to all the registered snmp
        managers for the corresponding outstanding alarms based on the severity value
        set in the object."
	::= { sysConfig 24 }

-- DNS related configuration objects

dnsDomainName OBJECT-TYPE
	SYNTAX DisplayString
	MAX-ACCESS read-write
	STATUS current
	DESCRIPTION
		"Domain name for the DNS servers."		
	::= { dnsConfig 1 }
	
dnsNextServerIndex		OBJECT-TYPE
	SYNTAX Integer32(0..1 | -1)
	MAX-ACCESS read-only
	STATUS current
	DESCRIPTION
		"Identifies a hint for the next value of dnsServerIndex to 
		be used in a row creation attempt for the dnsServerTable. 
		If no new rows can be created, this object will have a value
		of -1."
	::= { dnsConfig 2 }	

dnsServerTable OBJECT-TYPE
	SYNTAX SEQUENCE OF DnsServerEntry
	MAX-ACCESS not-accessible
	STATUS current
	DESCRIPTION
		"The table contains DNS Server configuration info."
	::= { dnsConfig 3 }

dnsServerEntry  OBJECT-TYPE
	SYNTAX DnsServerEntry
    MAX-ACCESS not-accessible
    STATUS current
    DESCRIPTION
		"An entry for DNS server"
    INDEX { dnsServerIndex }
    ::= { dnsServerTable 1 }

DnsServerEntry ::= SEQUENCE {
	dnsServerIndex		Integer32,
	dnsServerAddress	IpAddress,
	dnsServerRowStatus	RowStatus
	}

dnsServerIndex	OBJECT-TYPE
	SYNTAX Integer32 (0..1)
	MAX-ACCESS not-accessible
	STATUS current
	DESCRIPTION
		"DNS Server entry number in the DNS server table."
    ::= { dnsServerEntry 1 }

dnsServerAddress	OBJECT-TYPE
	SYNTAX IpAddress
	MAX-ACCESS read-create
	STATUS current
	DESCRIPTION
		"IP Address of the DNS Server."
    ::= { dnsServerEntry 2 }

dnsServerRowStatus    OBJECT-TYPE
	SYNTAX RowStatus
	MAX-ACCESS read-create
	STATUS current
	DESCRIPTION
		"The status of the row. Required to create or delete the entry in 
		this table. Only createAndGo method of row creation is supported 
		and createAndWait method is not supported."
	::= { dnsServerEntry 3 }    	
    
    		
-- MGCP related configuration objects

mgcpPort OBJECT-TYPE
	SYNTAX Integer32(1025..5099)
	MAX-ACCESS read-write
	STATUS current
	DESCRIPTION
		"MGCP port number."
	DEFVAL {2427}		
	::= { mgcpConfig 1 }
	
mgcpRequestTimeout OBJECT-TYPE
	SYNTAX Integer32(30..120)
	UNITS "seconds"
	MAX-ACCESS read-write
	STATUS current
	DESCRIPTION
		"Timeout value for MGCP requests."
	DEFVAL {30}
	::= { mgcpConfig 2 }	
	
mgcpRequestRetries OBJECT-TYPE
	SYNTAX Integer32(0..2147483647)
	MAX-ACCESS read-write
	STATUS current
	DESCRIPTION
		"Maximum number of retries for MGCP requests."
	DEFVAL {3}
	::= { mgcpConfig 3 }	
	
mgcpRestartDelay OBJECT-TYPE
	SYNTAX Integer32(0..2147483647)
	UNITS "seconds"
	MAX-ACCESS read-write
	STATUS current
	DESCRIPTION
		""
	DEFVAL {0}
	::= { mgcpConfig 4 }
	
mgcpErrorRateThreshold OBJECT-TYPE
	SYNTAX Integer32 
	MAX-ACCESS read-write
	STATUS current
	DESCRIPTION
		"Threshold value for MGCP error rate."
	::= { mgcpConfig 5 }

mgcpJitterThreshold OBJECT-TYPE
	SYNTAX Integer32 (0..2147483647)
	MAX-ACCESS read-write
	STATUS current
	DESCRIPTION
		"Threshold value for MGCP jitter."
	::= { mgcpConfig 6 }

mgcpLatencyThreshold OBJECT-TYPE
	SYNTAX Integer32 (0..2147483647)
	MAX-ACCESS read-write
	STATUS current
	DESCRIPTION
		"Threshold value for MGCP Latency."
	::= { mgcpConfig 7 }
	
mgcpPacketLossThreshold OBJECT-TYPE
	SYNTAX Integer32 
	MAX-ACCESS read-write
	STATUS current
	DESCRIPTION
		"Threshold value for MGCP Packet loss."
	::= { mgcpConfig 8 }
					 

mgcpNextCallAgentIndex		OBJECT-TYPE
	SYNTAX Integer32(0..14 | -1)
	MAX-ACCESS read-only
	STATUS current
	DESCRIPTION
		"Identifies a hint for the next value of mgcpCallAgentIndex to 
		be used in a row creation attempt for the mgcpCallAgentTable. 
		If no new rows can be created, this object will have a value
		of -1."
	::= { mgcpConfig 9 }
	
mgcpCallAgentTable		OBJECT-TYPE
	SYNTAX SEQUENCE OF MgcpCallAgentEntry
	MAX-ACCESS not-accessible
	STATUS current
	DESCRIPTION
		"The table is used for configuring MGCP Call Agent information."
	::= { mgcpConfig 10 }

mgcpCallAgentEntry  OBJECT-TYPE
	SYNTAX MgcpCallAgentEntry
    MAX-ACCESS not-accessible
    STATUS current
    DESCRIPTION
		"An entry for MGCP Call Agent."
    INDEX      { mgcpCallAgentIndex }
    ::= { mgcpCallAgentTable 1 }

MgcpCallAgentEntry ::= SEQUENCE {
	mgcpCallAgentIndex				Integer32,
	mgcpCallAgentLocalName			DisplayString,
	mgcpCallAgentAddress			DisplayString,
	mgcpCallAgentPort				Integer32,
	mgcpCallAgentRtpRtcpSecurity    INTEGER,
	mgcpCallAgentRowStatus			RowStatus,
	mgcpCallAgentPartition				Integer32
	}  
	
mgcpCallAgentIndex	OBJECT-TYPE
	SYNTAX Integer32(0..14)
	MAX-ACCESS not-accessible
	STATUS current
	DESCRIPTION
		"Call Agent number. Serves as index for this table."
    ::= { mgcpCallAgentEntry 1 }

mgcpCallAgentLocalName	OBJECT-TYPE
	SYNTAX DisplayString
	MAX-ACCESS read-create
	STATUS current
	DESCRIPTION
		"Name for MGCP Call Agent."
    ::= { mgcpCallAgentEntry 2 }
    
mgcpCallAgentAddress	OBJECT-TYPE
	SYNTAX DisplayString
	MAX-ACCESS read-create
	STATUS current
	DESCRIPTION
		"Host Name OR IP Address for MGCP Call Agent."
    ::= { mgcpCallAgentEntry 3 }
    
mgcpCallAgentPort	OBJECT-TYPE
	SYNTAX Integer32(1025..65535)
	MAX-ACCESS read-create
	STATUS current
	DESCRIPTION
		"Port number for MGCP Call Agent."
	DEFVAL {2427}                                  
    ::= { mgcpCallAgentEntry 4 }
    
mgcpCallAgentRtpRtcpSecurity	OBJECT-TYPE
	SYNTAX INTEGER {
		off(0),
		on(1)
	}
	MAX-ACCESS read-create
	STATUS current
	DESCRIPTION
		"To Turn the RTP-RTCP Security off or on."
	DEFVAL {off}
    ::= { mgcpCallAgentEntry 5 }
    
mgcpCallAgentRowStatus    OBJECT-TYPE
	SYNTAX RowStatus
	MAX-ACCESS read-create
	STATUS current
	DESCRIPTION
		"The status of the row. Required to create or delete the entry in 
		this table. Only createAndGo method of row creation is supported 
		and createAndWait method is not supported."
	::= { mgcpCallAgentEntry 6 }             

mgcpCallAgentPartition	OBJECT-TYPE
	SYNTAX Integer32
	MAX-ACCESS read-create
	STATUS current
	DESCRIPTION
		"Partition Number for MGCP Call Agent."
    ::= { mgcpCallAgentEntry 7 }
    
mgcpIvrEndPointTable		OBJECT-TYPE
	SYNTAX SEQUENCE OF MgcpIvrEndPointEntry
	MAX-ACCESS not-accessible
	STATUS obsolete
	DESCRIPTION
		"The table contains MGCP IVR endpoint configuration info."
	::= { mgcpConfig 11 }

mgcpIvrEndPointEntry  OBJECT-TYPE
	SYNTAX MgcpIvrEndPointEntry
    MAX-ACCESS not-accessible
    STATUS obsolete
    DESCRIPTION
		"An entry for MGCP IVR endpoint"
    INDEX      { mgcpIvrEndPointIndex }
    ::= { mgcpIvrEndPointTable 1 }

MgcpIvrEndPointEntry ::= SEQUENCE {
	mgcpIvrEndPointIndex		Integer32,
	mgcpIvrEndPointType			INTEGER,
	mgcpIvrEndPointName			DisplayString,
	mgcpIvrEndPointValue		Integer32,
	mgcpIvrEndPointRowStatus	RowStatus
	}

mgcpIvrEndPointIndex	OBJECT-TYPE
	SYNTAX Integer32 (0..4)
	MAX-ACCESS not-accessible
	STATUS obsolete
	DESCRIPTION
		"Endpoint entry number in the mgcp endpoint table."
    ::= { mgcpIvrEndPointEntry 1 }

mgcpIvrEndPointType	OBJECT-TYPE
	SYNTAX INTEGER {
		dynamic(1),
		static(2)
	}
	MAX-ACCESS read-create
	STATUS obsolete
	DESCRIPTION
		"Type of the ivr endpoint. Can be dynamic(1) or static(2). This column
		is must to create the entry in endpoint table."
    ::= { mgcpIvrEndPointEntry 2 }

mgcpIvrEndPointName	OBJECT-TYPE
	SYNTAX DisplayString
	MAX-ACCESS read-create
	STATUS obsolete
	DESCRIPTION
		"Name of the ivr endpoint. It is must to create the entry in endpoint 
		table."
    ::= { mgcpIvrEndPointEntry 3 }        		

mgcpIvrEndPointValue	OBJECT-TYPE
	SYNTAX Integer32(0 | 2..6000)
	MAX-ACCESS read-create
	STATUS obsolete
	DESCRIPTION
		"Value for static endpoint. Required to create static endpoint. For
		dynamic endpoint this column is not used and for dynamic endpoint
		MediaServer shows this value as 0."
    ::= { mgcpIvrEndPointEntry 4 }
    
mgcpIvrEndPointRowStatus    OBJECT-TYPE
	SYNTAX RowStatus
	MAX-ACCESS read-create
	STATUS obsolete
	DESCRIPTION
		"The status of the row. Required to create or delete the entry in 
		this table. Only createAndGo method of row creation is supported 
		and createAndWait method is not supported."
	::= { mgcpIvrEndPointEntry 5 }    	

mgcpConfEndPointTable		OBJECT-TYPE
	SYNTAX SEQUENCE OF MgcpConfEndPointEntry
	MAX-ACCESS not-accessible
	STATUS obsolete
	DESCRIPTION
		"The table contains MGCP Conf endpoint configuration info."
	::= { mgcpConfig 12 }

mgcpConfEndPointEntry  OBJECT-TYPE
	SYNTAX MgcpConfEndPointEntry
    MAX-ACCESS not-accessible
    STATUS obsolete
    DESCRIPTION
		"An entry for MGCP Conf endpoint"
    INDEX      { mgcpConfEndPointIndex }
    ::= { mgcpConfEndPointTable 1 }

MgcpConfEndPointEntry ::= SEQUENCE {
	mgcpConfEndPointIndex		Integer32,
	mgcpConfEndPointType			INTEGER,
	mgcpConfEndPointName			DisplayString,
	mgcpConfEndPointValue		Integer32,
	mgcpConfEndPointRowStatus	RowStatus
	}

mgcpConfEndPointIndex	OBJECT-TYPE
	SYNTAX Integer32 (0..4)
	MAX-ACCESS not-accessible
	STATUS obsolete
	DESCRIPTION
		"Endpoint entry number in the mgcp endpoint table."
    ::= { mgcpConfEndPointEntry 1 }

mgcpConfEndPointType	OBJECT-TYPE
	SYNTAX INTEGER {
		dynamic(1),
		static(2)
	}
	MAX-ACCESS read-create
	STATUS obsolete
	DESCRIPTION
		"Type of the conf endpoint. Can be static(2) or dynamic(1). This column
		is must to create the entry in endpoint table."
    ::= { mgcpConfEndPointEntry 2 }

mgcpConfEndPointName	OBJECT-TYPE
	SYNTAX DisplayString
	MAX-ACCESS read-create
	STATUS obsolete
	DESCRIPTION
		"Name of the conf endpoint. It is must to create the entry in endpoint 
		table."
    ::= { mgcpConfEndPointEntry 3 }        		

mgcpConfEndPointValue	OBJECT-TYPE
	SYNTAX Integer32(0 | 2..6000)
	MAX-ACCESS read-create
	STATUS obsolete
	DESCRIPTION
		"Value for static endpoint. Required to create static endpoint. For
		dynamic endpoint this column is not used and for dynamic endpoint
		MediaServer shows this value as 0."
    ::= { mgcpConfEndPointEntry 4 }
    
mgcpConfEndPointRowStatus    OBJECT-TYPE
	SYNTAX RowStatus
	MAX-ACCESS read-create
	STATUS obsolete
	DESCRIPTION
		"The status of the row. Required to create or delete the entry in 
		this table. Only createAndGo method of row creation is supported 
		and createAndWait method is not supported."
	::= { mgcpConfEndPointEntry 5 }    

mgcpAhConfEndPointTable		OBJECT-TYPE
	SYNTAX SEQUENCE OF MgcpAhConfEndPointEntry
	MAX-ACCESS not-accessible
	STATUS obsolete
	DESCRIPTION
		"The table contains MGCP Adhoc Conf endpoint configuration info."
	::= { mgcpConfig 13 }

mgcpAhConfEndPointEntry  OBJECT-TYPE
	SYNTAX MgcpAhConfEndPointEntry
    MAX-ACCESS not-accessible
    STATUS obsolete
    DESCRIPTION
		"An entry for MGCP Adhoc Conf endpoint"
    INDEX      { mgcpAhConfEndPointIndex }
    ::= { mgcpAhConfEndPointTable 1 }

MgcpAhConfEndPointEntry ::= SEQUENCE {
	mgcpAhConfEndPointIndex		Integer32,
	mgcpAhConfEndPointType		INTEGER,
	mgcpAhConfEndPointName		DisplayString,
	mgcpAhConfEndPointValue		Integer32,
	mgcpAhConfEndPointRowStatus	RowStatus
	}

mgcpAhConfEndPointIndex	OBJECT-TYPE
	SYNTAX Integer32 (0..4)
	MAX-ACCESS not-accessible
	STATUS obsolete
	DESCRIPTION
		"Endpoint entry number in the mgcp endpoint table."
    ::= { mgcpAhConfEndPointEntry 1 }

mgcpAhConfEndPointType	OBJECT-TYPE
	SYNTAX INTEGER {
		dynamic(1),
		static(2)
	}
	MAX-ACCESS read-create
	STATUS obsolete
	DESCRIPTION
		"Type of the adhoc conf endpoint. Can be static(2) or dynamic(1). This column
		is must to create the entry in endpoint table."
    ::= { mgcpAhConfEndPointEntry 2 }

mgcpAhConfEndPointName	OBJECT-TYPE
	SYNTAX DisplayString
	MAX-ACCESS read-create
	STATUS obsolete
	DESCRIPTION
		"Name of the adhoc conf endpoint. It is must to create the entry in endpoint 
		table."
    ::= { mgcpAhConfEndPointEntry 3 }        		

mgcpAhConfEndPointValue	OBJECT-TYPE
	SYNTAX Integer32(0 | 2..6000)
	MAX-ACCESS read-create
	STATUS obsolete
	DESCRIPTION
		"Value for static endpoint. Required to create static endpoint. For
		dynamic endpoint this column is not used and for dynamic endpoint
		MediaServer shows this value as 0."
    ::= { mgcpAhConfEndPointEntry 4 }
    
mgcpAhConfEndPointRowStatus    OBJECT-TYPE
	SYNTAX RowStatus
	MAX-ACCESS read-create
	STATUS obsolete
	DESCRIPTION
		"The status of the row. Required to create or delete the entry in 
		this table. Only createAndGo method of row creation is supported 
		and createAndWait method is not supported."
	::= { mgcpAhConfEndPointEntry 5 }	

mgcpFaxEndPointTable		OBJECT-TYPE
	SYNTAX SEQUENCE OF MgcpFaxEndPointEntry
	MAX-ACCESS not-accessible
	STATUS obsolete
	DESCRIPTION
		"The table contains MGCP IVR endpoint configuration info."
	::= { mgcpConfig 14 }

mgcpFaxEndPointEntry  OBJECT-TYPE
	SYNTAX MgcpFaxEndPointEntry
    MAX-ACCESS not-accessible
    STATUS obsolete
    DESCRIPTION
		"An entry for MGCP fax endpoint"
    INDEX      { mgcpFaxEndPointIndex }
    ::= { mgcpFaxEndPointTable 1 }

MgcpFaxEndPointEntry ::= SEQUENCE {
	mgcpFaxEndPointIndex		Integer32,
	mgcpFaxEndPointType			INTEGER,
	mgcpFaxEndPointName			DisplayString,
	mgcpFaxEndPointValue		Integer32,
	mgcpFaxEndPointRowStatus	RowStatus
	}

mgcpFaxEndPointIndex	OBJECT-TYPE
	SYNTAX Integer32 (0..4)
	MAX-ACCESS not-accessible
	STATUS obsolete
	DESCRIPTION
		"Endpoint entry number in the mgcp endpoint table."
    ::= { mgcpFaxEndPointEntry 1 }

mgcpFaxEndPointType	OBJECT-TYPE
	SYNTAX INTEGER {
		dynamic(1),
		static(2)
	}
	MAX-ACCESS read-create
	STATUS obsolete
	DESCRIPTION
		"Type of the fax endpoint. Can be dynamic(1) or static(2). This column
		is must to create the entry in endpoint table."
    ::= { mgcpFaxEndPointEntry 2 }

mgcpFaxEndPointName	OBJECT-TYPE
	SYNTAX DisplayString
	MAX-ACCESS read-create
	STATUS obsolete
	DESCRIPTION
		"Name of the fax endpoint. It is must to create the entry in endpoint 
		table."
    ::= { mgcpFaxEndPointEntry 3 }        		

mgcpFaxEndPointValue	OBJECT-TYPE
	SYNTAX Integer32(0 | 2..6000)
	MAX-ACCESS read-create
	STATUS obsolete
	DESCRIPTION
		"Value for static endpoint. Required to create static endpoint. For
		dynamic endpoint this column is not used and for dynamic endpoint
		MediaServer shows this value as 0."
    ::= { mgcpFaxEndPointEntry 4 }
    
mgcpFaxEndPointRowStatus    OBJECT-TYPE
	SYNTAX RowStatus
	MAX-ACCESS read-create
	STATUS obsolete
	DESCRIPTION
		"The status of the row. Required to create or delete the entry in 
		this table. Only createAndGo method of row creation is supported 
		and createAndWait method is not supported."
	::= { mgcpFaxEndPointEntry 5 }    	

-- SIP related configuration objects

sipPort OBJECT-TYPE
	SYNTAX Integer32(1025..5099)
	MAX-ACCESS read-write
	STATUS current
	DESCRIPTION
		"SIP Port value"
	DEFVAL {5060}
	::= { sipConfig 1 }	
	
sipRequestRetries OBJECT-TYPE
	SYNTAX Integer32(0..100)
	MAX-ACCESS read-write
	STATUS current
	DESCRIPTION
		"Max number of retries for SIP requests."
	DEFVAL {7}
	::= { sipConfig 2 }	

sipResponseRetries OBJECT-TYPE
	SYNTAX Integer32(0..100)
	MAX-ACCESS read-write
	STATUS current
	DESCRIPTION
		"Max number of retries for SIP responses."
	DEFVAL {7}
	::= { sipConfig 3 }

sipNextCallAgentIndex		OBJECT-TYPE
	SYNTAX Integer32(0..1 | -1)
	MAX-ACCESS read-only
	STATUS current
	DESCRIPTION
		"Identifies a hint for the next value of sipCallAgentIndex to 
		be used in a row creation attempt for the sipCallAgentTable. 
		If no new rows can be created, this object will have a value
		of -1."
	::= { sipConfig 4 }		

sipCallAgentTable		OBJECT-TYPE
	SYNTAX SEQUENCE OF SipCallAgentEntry
	MAX-ACCESS not-accessible
	STATUS current
	DESCRIPTION
		"The table is used for configuring SIP Call Agent information."
	::= { sipConfig 5 }

sipCallAgentEntry  OBJECT-TYPE
	SYNTAX SipCallAgentEntry
    MAX-ACCESS not-accessible
    STATUS current
    DESCRIPTION
		"An entry for SIP Call Agent."
    INDEX      { sipCallAgentIndex }
    ::= { sipCallAgentTable 1 }

SipCallAgentEntry ::= SEQUENCE {
	sipCallAgentIndex		Integer32,
	sipCallAgentLocalName	DisplayString,
	sipCallAgentAddress		DisplayString,
	sipCallAgentPort		Integer32,
	sipCallAgentPassword    DisplayString,
	sipCallAgentRowStatus	RowStatus,	
	sipCallAgentPartition	Integer32	
	}  
	
sipCallAgentIndex	OBJECT-TYPE
	SYNTAX Integer32(0..1)
	MAX-ACCESS not-accessible
	STATUS current
	DESCRIPTION
		"Call Agent number. Serves as index for this table."
    ::= { sipCallAgentEntry 1 }

sipCallAgentLocalName	OBJECT-TYPE
	SYNTAX DisplayString
	MAX-ACCESS read-create
	STATUS current
	DESCRIPTION
		"Name for SIP Call Agent."
    ::= { sipCallAgentEntry 2 }
    
sipCallAgentAddress	OBJECT-TYPE
	SYNTAX DisplayString
	MAX-ACCESS read-create
	STATUS current
	DESCRIPTION
		"Host Name OR IP Address for SIP Call Agent."
    ::= { sipCallAgentEntry 3 }
    
sipCallAgentPort	OBJECT-TYPE
	SYNTAX Integer32(1024..5099)
	MAX-ACCESS read-create
	STATUS current
	DESCRIPTION
		"Port number for SIP Call Agent."
	DEFVAL {5060}
    ::= { sipCallAgentEntry 4 }
    
sipCallAgentPassword	OBJECT-TYPE
	SYNTAX DisplayString
	MAX-ACCESS read-create
	STATUS current
	DESCRIPTION
		"Password for SIP Call Agent."
    ::= { sipCallAgentEntry 5 }

sipCallAgentRowStatus    OBJECT-TYPE
	SYNTAX RowStatus
	MAX-ACCESS read-create
	STATUS current
	DESCRIPTION
		"The status of the row. Required to create or delete the entry in 
		this table. Only createAndGo method of row creation is supported 
		and createAndWait method is not supported."
	::= { sipCallAgentEntry 6 }	

sipCallAgentPartition	OBJECT-TYPE
	SYNTAX Integer32
	MAX-ACCESS read-create
	STATUS current
	DESCRIPTION
		"Partition Number for Sip Call Agent."
    ::= { sipCallAgentEntry 7 }
    
sipProxyNextCallAgentIndex OBJECT-TYPE
	SYNTAX Integer32(0..1 | -1)
	MAX-ACCESS read-only
	STATUS current
	DESCRIPTION
		"Identifies a hint for the next value of sipProxyCallAgentIndex to 
		be used in a row creation attempt for the sipProxyCallAgentTable. 
		If no new rows can be created, this object will have a value
		of -1."
	::= { sipConfig 6 }    
	
sipProxyCallAgentTable		OBJECT-TYPE
	SYNTAX SEQUENCE OF SipProxyCallAgentEntry
	MAX-ACCESS not-accessible
	STATUS current
	DESCRIPTION
		"The table is used for configuring SIP Proxy Call Agent 
		information."
	::= { sipConfig 7 }

sipProxyCallAgentEntry  OBJECT-TYPE
	SYNTAX SipProxyCallAgentEntry
    MAX-ACCESS not-accessible
    STATUS current
    DESCRIPTION
		"An entry for SIP Proxy Call Agent."
    INDEX      { sipProxyCallAgentIndex }
    ::= { sipProxyCallAgentTable 1 }

SipProxyCallAgentEntry ::= SEQUENCE {
	sipProxyCallAgentIndex		Integer32,
	sipProxyCallAgentLocalName	DisplayString,
	sipProxyCallAgentAddress	DisplayString,
	sipProxyCallAgentPort		Integer32,
	sipProxyCallAgentPassword   DisplayString,
	sipProxyCallAgentRowStatus	RowStatus	
	}  
	
sipProxyCallAgentIndex	OBJECT-TYPE
	SYNTAX Integer32(0..1)
	MAX-ACCESS not-accessible
	STATUS current
	DESCRIPTION
		"SIP Proxy Call Agent number. Serves as index for this table."
    ::= { sipProxyCallAgentEntry 1 }

sipProxyCallAgentLocalName	OBJECT-TYPE
	SYNTAX DisplayString
	MAX-ACCESS read-create
	STATUS current
	DESCRIPTION
		"Name for SIP Proxy Call Agent."
    ::= { sipProxyCallAgentEntry 2 }
    
sipProxyCallAgentAddress	OBJECT-TYPE
	SYNTAX DisplayString
	MAX-ACCESS read-create
	STATUS current
	DESCRIPTION
		"Host Name OR IP Address for SIP Proxy Call Agent."
    ::= { sipProxyCallAgentEntry 3 }
    
sipProxyCallAgentPort	OBJECT-TYPE
	SYNTAX Integer32(1024..5099)
	MAX-ACCESS read-create
	STATUS current
	DESCRIPTION
		"Port number for SIP Proxy Call Agent."
	DEFVAL {5060}
    ::= { sipProxyCallAgentEntry 4 }
    
sipProxyCallAgentPassword	OBJECT-TYPE
	SYNTAX DisplayString
	MAX-ACCESS read-create
	STATUS current
	DESCRIPTION
		"Password for SIP Proxy Call Agent."
    ::= { sipProxyCallAgentEntry 5 }
    
sipProxyCallAgentRowStatus    OBJECT-TYPE
	SYNTAX RowStatus
	MAX-ACCESS read-create
	STATUS current
	DESCRIPTION
		"The status of the row. Required to create or delete the entry in 
		this table. Only createAndGo method of row creation is supported 
		and createAndWait method is not supported."
	::= { sipProxyCallAgentEntry 6 }                 

sipIvrServiceTable		OBJECT-TYPE
	SYNTAX SEQUENCE OF SipIvrServiceEntry
	MAX-ACCESS not-accessible
	STATUS current
	DESCRIPTION
		"The table is used for configuring SIP Service information for IVR."
	::= { sipConfig 8 }

sipIvrServiceEntry  OBJECT-TYPE
	SYNTAX SipIvrServiceEntry
    MAX-ACCESS not-accessible
    STATUS current
    DESCRIPTION
		"An entry for SIP service."
    INDEX      { sipIvrServiceIndex }
    ::= { sipIvrServiceTable 1 }

SipIvrServiceEntry ::= SEQUENCE {
	sipIvrServiceIndex		Integer32,
	sipIvrServiceDialog		DisplayString,
	sipIvrServiceRowStatus	RowStatus
	}  

sipIvrServiceIndex	OBJECT-TYPE
	SYNTAX Integer32(0..1)
	MAX-ACCESS not-accessible
	STATUS current
	DESCRIPTION
		"Index for this table."
    ::= { sipIvrServiceEntry 1 }
        
sipIvrServiceDialog	OBJECT-TYPE
	SYNTAX DisplayString
	MAX-ACCESS read-create
	STATUS current
	DESCRIPTION
		"Dialog name for the service"
    ::= { sipIvrServiceEntry 2 }

sipIvrServiceRowStatus    OBJECT-TYPE
	SYNTAX RowStatus
	MAX-ACCESS read-create
	STATUS current
	DESCRIPTION
		"The status of the row. Required to create or delete the entry in 
		this table. Only createAndGo method of row creation is supported 
		and createAndWait method is not supported."
	::= { sipIvrServiceEntry 3 }            

sipConfServiceTable		OBJECT-TYPE
	SYNTAX SEQUENCE OF SipConfServiceEntry
	MAX-ACCESS not-accessible
	STATUS current
	DESCRIPTION
		"The table is used for configuring SIP Service information for Conf."
	::= { sipConfig 9 }

sipConfServiceEntry  OBJECT-TYPE
	SYNTAX SipConfServiceEntry
    MAX-ACCESS not-accessible
    STATUS current
    DESCRIPTION
		"An entry for conf SIP service."
    INDEX      { sipConfServiceIndex }
    ::= { sipConfServiceTable 1 }

SipConfServiceEntry ::= SEQUENCE {
	sipConfServiceIndex		Integer32,
	sipConfServiceDialog	DisplayString,
	sipConfServiceRowStatus	RowStatus
	}  

sipConfServiceIndex	OBJECT-TYPE
	SYNTAX Integer32(0..1)
	MAX-ACCESS not-accessible
	STATUS current
	DESCRIPTION
		"Index for this table."
    ::= { sipConfServiceEntry 1 }
        
sipConfServiceDialog	OBJECT-TYPE
	SYNTAX DisplayString
	MAX-ACCESS read-create
	STATUS current
	DESCRIPTION
		"Dialog name for the service"
    ::= { sipConfServiceEntry 2 }

sipConfServiceRowStatus    OBJECT-TYPE
	SYNTAX RowStatus
	MAX-ACCESS read-create
	STATUS current
	DESCRIPTION
		"The status of the row. Required to create or delete the entry in 
		this table. Only createAndGo method of row creation is supported 
		and createAndWait method is not supported."
	::= { sipConfServiceEntry 3 }            

sipAhConfServiceTable		OBJECT-TYPE
	SYNTAX SEQUENCE OF SipAhConfServiceEntry
	MAX-ACCESS not-accessible
	STATUS current
	DESCRIPTION
		"The table is used for configuring SIP Service information for Conf."
	::= { sipConfig 10 }

sipAhConfServiceEntry  OBJECT-TYPE
	SYNTAX SipAhConfServiceEntry
    MAX-ACCESS not-accessible
    STATUS current
    DESCRIPTION
		"An entry for Adhoc conf SIP service."
    INDEX      { sipAhConfServiceIndex }
    ::= { sipAhConfServiceTable 1 }

SipAhConfServiceEntry ::= SEQUENCE {
	sipAhConfServiceIndex		Integer32,
	sipAhConfServiceDialog		DisplayString,
	sipAhConfServiceRowStatus	RowStatus
	}  

sipAhConfServiceIndex	OBJECT-TYPE
	SYNTAX Integer32(0..1)
	MAX-ACCESS not-accessible
	STATUS current
	DESCRIPTION
		"Index for this table."
    ::= { sipAhConfServiceEntry 1 }
        
sipAhConfServiceDialog	OBJECT-TYPE
	SYNTAX DisplayString
	MAX-ACCESS read-create
	STATUS current
	DESCRIPTION
		"Dialog name for the service"
    ::= { sipAhConfServiceEntry 2 }

sipAhConfServiceRowStatus    OBJECT-TYPE
	SYNTAX RowStatus
	MAX-ACCESS read-create
	STATUS current
	DESCRIPTION
		"The status of the row. Required to create or delete the entry in 
		this table. Only createAndGo method of row creation is supported 
		and createAndWait method is not supported."
	::= { sipAhConfServiceEntry 3 }            

	
-- SIP DNIS Map scripts objects   

ipUnitySipDnisMappingNextNum      OBJECT-TYPE
    SYNTAX Integer32(0..24 | -1)
    MAX-ACCESS read-only
    STATUS current
    DESCRIPTION
        "Identifies a hint for the next value of ipUnitySipDnisMappingNum to
        be used in a row creation attempt for the ipUnitySipDnisMappingTable.
        If no new rows can be created, this object will have a value
        of 0."
    ::= { sipConfig 11 }

ipUnitySipDnisMappingTable		OBJECT-TYPE
	SYNTAX SEQUENCE OF SipDnisMappingEntry
	MAX-ACCESS not-accessible
	STATUS current
	DESCRIPTION
		"The table is used for configuring SIP DNIS Map scripts."
	::= { sipConfig 12 }

ipUnitySipDnisMappingEntry  OBJECT-TYPE
	SYNTAX SipDnisMappingEntry
    MAX-ACCESS not-accessible
    STATUS current
    DESCRIPTION
		"An entry for SIP DNIS Map scripts."
    INDEX      { ipUnitySipDnisMappingIndex }
    ::= { ipUnitySipDnisMappingTable 2 }

SipDnisMappingEntry ::= SEQUENCE {
	ipUnitySipDnisMappingIndex		Integer32,
	ipUnitySipDnisMappingNumber	DisplayString,
	ipUnitySipDnisMappingScript	DisplayString,
	ipUnitySipDnisMappingRowStatus	RowStatus
	}  

ipUnitySipDnisMappingIndex	OBJECT-TYPE
	SYNTAX Integer32(0..24)
	MAX-ACCESS not-accessible
	STATUS current
	DESCRIPTION
		"Index for this table."
    ::= { ipUnitySipDnisMappingEntry 1 }
        
ipUnitySipDnisMappingNumber	OBJECT-TYPE
	SYNTAX DisplayString
	MAX-ACCESS read-create
	STATUS current
	DESCRIPTION
		"Sip dnis map index number."
    ::= { ipUnitySipDnisMappingEntry 2 }

ipUnitySipDnisMappingScript	OBJECT-TYPE
	SYNTAX DisplayString
	MAX-ACCESS read-create
	STATUS current
	DESCRIPTION
		"The Sip dnis map script."
    ::= { ipUnitySipDnisMappingEntry 3 }

ipUnitySipDnisMappingRowStatus    OBJECT-TYPE
	SYNTAX RowStatus
	MAX-ACCESS read-create
	STATUS current
	DESCRIPTION   
		"The status of the row. Required to create or delete the entry in 
		this table. Only createAndGo method of row creation is supported 
		and createAndWait method is not supported."
	::= { ipUnitySipDnisMappingEntry 4 } 

ipUnitySipDtmfTransfer       OBJECT-TYPE
   SYNTAX INTEGER {
        off (0),
        on (1)
    }
    MAX-ACCESS read-write
    STATUS current
    DESCRIPTION
        "Enable or disable the sip DMTF transfer mode."
   ::= { sipConfig 13 }

ipUnitySipAuthorization    OBJECT-TYPE
    SYNTAX INTEGER {
        off (0),
        on (1)
    }
    MAX-ACCESS read-write
    STATUS current
    DESCRIPTION
        "Enable or disable the sip authorization."
    DEFVAL {off}
    ::= { sipConfig 14 }

ipUnitySipImsNetwork      OBJECT-TYPE
        SYNTAX INTEGER {
                no(0),
                yes(1)
        }
        MAX-ACCESS read-create
        STATUS current
        DESCRIPTION
                ""
        DEFVAL  {no}
    ::= { sipConfig 15 }

-- RTP configuration objects 

rtpCodecPriorityList1 OBJECT-TYPE
	SYNTAX INTEGER {
		g711u (0), 
		g711a (8), 
		g729a (18), 
		g723 (4),
		gsm-amr (19),
                gsm-efr (20),
		evrc (23), 
		evrc0 (28) 

	}
	MAX-ACCESS read-write
	STATUS current
	DESCRIPTION
		"First rtp codec in the priority list. Remaining seven codec values should
		be different ones. Set operation is performed only when all the eight codec
		values are passed in one SNMP set request."
	::= { rtpConfig 1 }

rtpCodecPriorityList2 OBJECT-TYPE
	SYNTAX INTEGER {
		g711u (0), 
		g711a (8), 
		g729a (18), 
		g723 (4),
		gsm-amr (19),
                gsm-efr (20),
		evrc (23), 
		evrc0 (28) 

	}
	MAX-ACCESS read-write
	STATUS current
	DESCRIPTION
		"Second rtp codec in the priority list. Remaining seven codec values should
		be different ones. Set operation is performed only when all the eight codec
		values are passed in one SNMP set request."
	::= { rtpConfig 2 }

rtpCodecPriorityList3 OBJECT-TYPE
	SYNTAX INTEGER {
		g711u (0), 
		g711a (8), 
		g729a (18), 
		g723 (4),
		gsm-amr (19),
                gsm-efr (20),
		evrc (23), 
		evrc0 (28) 

	}
	MAX-ACCESS read-write
	STATUS current
	DESCRIPTION
		"Third rtp codec in the priority list. Remaining seven codec values should
		be different ones. Set operation is performed only when all the eight codec
		values are passed in one SNMP set request."
	::= { rtpConfig 3 }

rtpCodecPriorityList4 OBJECT-TYPE
	SYNTAX INTEGER {
		g711u (0), 
		g711a (8), 
		g729a (18), 
		g723 (4),
		gsm-amr (19),
                gsm-efr (20),
		evrc (23), 
		evrc0 (28) 

	
	}
	MAX-ACCESS read-write
	STATUS current
	DESCRIPTION
		"Fourth rtp codec in the priority list. Remaining seven codec values should
		be different ones. Set operation is performed only when all the eight codec
		values are passed in one SNMP set request."
	::= { rtpConfig 4 }		
			
rtpPayloadSizeList OBJECT-TYPE
	SYNTAX OCTET STRING (SIZE(1..3))
	MAX-ACCESS read-write
	STATUS current
	DESCRIPTION
		"Default RTP payload size list. This object takes upto 3 payload 
		sizes, each payload size in one byte. Each byte can contain a value
		of either 10, 20 or 30. Same value can not be repeated in the list.
		
		Some examples are (10, 30); (20, 10, 30); (30)."
	::= { rtpConfig 5 }
	
rtpSilenceSuppression OBJECT-TYPE
	SYNTAX INTEGER {
		off (0),
		on (1)
	}
	MAX-ACCESS read-write
	STATUS current
	DESCRIPTION
		"Silence suppression flag for RTP."
	::= { rtpConfig 6 }

rtpCodecPriorityList5 OBJECT-TYPE
	SYNTAX INTEGER {
		g711u (0), 
		g711a (8), 
		g729a (18), 
		g723 (4),
		gsm-amr (19),
                gsm-efr (20),
		evrc (23), 
		evrc0 (28) 
	
	}
	MAX-ACCESS read-write
	STATUS current
	DESCRIPTION
		"Fifth rtp codec in the priority list. Remaining seven codec values should
		be different ones. Set operation is performed only when all the eight codec
		values are passed in one SNMP set request."
	::= { rtpConfig 7 }		
			

rtpCodecPriorityList6 OBJECT-TYPE
	SYNTAX INTEGER {
		g711u (0), 
		g711a (8), 
		g729a (18), 
		g723 (4),
		gsm-amr (19),
                gsm-efr (20),
		evrc (23), 
		evrc0 (28) 

	}
	MAX-ACCESS read-write
	STATUS current
	DESCRIPTION
		"Sixth rtp codec in the priority list. Remaining seven codec values should
		be different ones. Set operation is performed only when all the eight codec
		values are passed in one SNMP set request."
	::= { rtpConfig 8 }

rtpPortRangeStart OBJECT-TYPE
	SYNTAX Integer32(0..65535)
	MAX-ACCESS read-write
	STATUS current
	DESCRIPTION
		"Minimum value of RTP/RTCP port. The RTP/RTCP port defined should be greater then this value."
	DEFVAL {16000}
        ::= { rtpConfig 9 }		

rtpPortRangeEnd OBJECT-TYPE
	SYNTAX Integer32(0..65535)
	MAX-ACCESS read-write
	STATUS current
	DESCRIPTION
		"Maximum value of RTP/RTCP port. The RTP/RTCP port defined should be lesser then this value."
	DEFVAL {65535}
        ::= { rtpConfig 10 }		

ipUnityRtpVideoCodec OBJECT-TYPE
	SYNTAX INTEGER {
		h263  (1),
		h264  (2),
		mpeg4 (3)

	}
	MAX-ACCESS read-write
	STATUS current
	DESCRIPTION
		"Video Codec for the system." 
	::= { rtpConfig 11 }

ipUnityRtpVideoRecordingFormat OBJECT-TYPE
	SYNTAX INTEGER {
		format3gp (6)

	}
	MAX-ACCESS read-only
	STATUS current
	DESCRIPTION
		"Video recording format." 
	::= { rtpConfig 12 }

rtpDynamicPayloadGsmAmrVal OBJECT-TYPE
	SYNTAX Integer32(96..127)
	MAX-ACCESS read-write
	STATUS current
	DESCRIPTION
		"Gsm-amr dynamic payload."
	DEFVAL {104}
        ::= { rtpConfig 13 }		

rtpDynamicPayloadGsmAmrMode OBJECT-TYPE
	SYNTAX Integer32(0..7)
	MAX-ACCESS read-write
	STATUS current
	DESCRIPTION
		"Gsm-amr mode."
        ::= { rtpConfig 14 }		

rtpDynamicPayloadTelephoneEvent OBJECT-TYPE
	SYNTAX Integer32(96..127)
	MAX-ACCESS read-write
	STATUS current
	DESCRIPTION
		"Gsm-efr dynamic payload."
	DEFVAL {105}
        ::= { rtpConfig 15 }		

rtpDynamicPayloadGsmEfr OBJECT-TYPE
	SYNTAX Integer32(96..127)
	MAX-ACCESS read-write
	STATUS current
	DESCRIPTION
		"Gsm-efr dynamic payload."
	DEFVAL {106}
        ::= { rtpConfig 16 }		

rtpDynamicPayloadEvrc OBJECT-TYPE
	SYNTAX Integer32(96..127)
	MAX-ACCESS read-write
	STATUS current
	DESCRIPTION
		"Evrc dynamic payload."
	DEFVAL {107}
        ::= { rtpConfig 17 }		

rtpDynamicPayloadMpeg4 OBJECT-TYPE
	SYNTAX Integer32(96..127)
	MAX-ACCESS read-write
	STATUS current
	DESCRIPTION
		"Mpeg4 Dynamic payload."
	DEFVAL {120}
        ::= { rtpConfig 18 }		

rtpCodecPriorityList7 OBJECT-TYPE
	SYNTAX INTEGER {
		g711u (0), 
		g711a (8), 
		g729a (18), 
		g723 (4),
		gsm-amr (19),
                gsm-efr (20),
		evrc (23), 
		evrc0 (28) 

	}
	MAX-ACCESS read-write
	STATUS current
	DESCRIPTION
		"Seventh rtp codec in the priority list. Remaining seven codec values should
		be different ones. Set operation is performed only when all the eight codec
		values are passed in one SNMP set request."
	::= { rtpConfig 19 }

rtpCodecPriorityList8 OBJECT-TYPE
	SYNTAX INTEGER {
		g711u (0), 
		g711a (8), 
		g729a (18), 
		g723 (4),
		gsm-amr (19),
                gsm-efr (20),
		evrc (23), 
		evrc0 (28) 
	}
	MAX-ACCESS read-write
	STATUS current
	DESCRIPTION
		"Eighth rtp codec in the priority list. Remaining seven codec values should
		be different ones. Set operation is performed only when all the eight codec
		values are passed in one SNMP set request."
	::= { rtpConfig 20 }

rtpDynamicPayloadEvrc0 OBJECT-TYPE
	SYNTAX Integer32(96..127)
	MAX-ACCESS read-write
	STATUS current
	DESCRIPTION
		"Evrc0 dynamic payload."
	DEFVAL {109}
        ::= { rtpConfig 21 }		

rtpVideoCodecPriorityList1 OBJECT-TYPE
        SYNTAX INTEGER {
	h263 (1),
	h264 (2)
	}
        MAX-ACCESS read-write
        STATUS current
	DESCRIPTION
	   "First rtp video codec in the priority list. Remaining one codec values should be different from other. Set operation is performed only when all the video codec values are passed in one SNMP set request."
	::= { rtpConfig 22 }

rtpVideoCodecPriorityList2 OBJECT-TYPE
      SYNTAX INTEGER {
      h263 (1),
      h264 (2)
      }
      MAX-ACCESS read-write
      STATUS current
      DESCRIPTION
       "Second rtp video codec in the priority list. Remaining one codec values should be different from other. Set operation is performed only when all the video codec values are passed in one SNMP set request."
       ::= { rtpConfig 23 }

-- HTTP configuration objects

httpRevalidation    OBJECT-TYPE
	SYNTAX INTEGER {
		off (0),
		on (1)
	}
	MAX-ACCESS read-write
	STATUS current
	DESCRIPTION
		"Revalidation flag for HTTP."
	DEFVAL {off}
	::= { httpConfig 1 }

httpConnectionMaxLife    OBJECT-TYPE
	SYNTAX Integer32(0..100000)
	UNITS "Minutes"
	MAX-ACCESS read-write
	STATUS current
	DESCRIPTION
		"Maximum life of HTTP connection in minutes."
	DEFVAL {2880}
	::= { httpConfig 2 }

httpLowerThreshold    OBJECT-TYPE
	SYNTAX Integer32(0..100)
	MAX-ACCESS read-write
	STATUS current
	DESCRIPTION
		"Lowerbound value for HTTP Threshold."
	DEFVAL {50}
	::= { httpConfig 3 }

httpUpperThreshold    OBJECT-TYPE
	SYNTAX Integer32(0..100)
	MAX-ACCESS read-write
	STATUS current
	DESCRIPTION
		"Upperbound value for HTTP Threshold."
	DEFVAL {80}
	::= { httpConfig 4 }			

-- ASR configuration objects
asrResourcePolicy		OBJECT-TYPE
	SYNTAX INTEGER {
		guarantee(1),
		best-effort(2)
	}
	MAX-ACCESS read-write
	STATUS current
	DESCRIPTION
		"Configures the ASR Resource Policy."
	DEFVAL {best-effort}
	::= { asrConfig 1 }

asrPackageName	OBJECT-TYPE
	SYNTAX DisplayString (SIZE(1..255))
	MAX-ACCESS read-write
	STATUS current
	DESCRIPTION
		"Name of the ASR Package. This variable can not be set alone. 
		User needs to pass asrPackagePath value also in the same SET
		request."
    ::= { asrConfig 2 }

asrPackagePath	OBJECT-TYPE
	SYNTAX DisplayString (SIZE(1..255))
	MAX-ACCESS read-write
	STATUS current
	DESCRIPTION
		"Path and filename of the ASR Package. This variable can not 
		be set alone. User needs to pass asrPackageName value also in 
		the same SET request."
    ::= { asrConfig 3 }

-- TTS configurations

ttsAddress	OBJECT-TYPE
	SYNTAX DisplayString
	MAX-ACCESS read-write
	STATUS current
	DESCRIPTION
		"IP Address or hostname of TTS.Set operation is performed when both 
         ttsAddress and ttsPort are set in one SNMP set request or only ttsAddress is set."
    ::= { asrConfig 4 }

ttsPort	OBJECT-TYPE
	SYNTAX Integer32 (1025..65535)
	MAX-ACCESS read-write
	STATUS current
	DESCRIPTION
		"Port Number of TTS."
	DEFVAL {5080}
    ::= { asrConfig 5 }

ttsTimer OBJECT-TYPE
	SYNTAX Integer32 (0..2147483647)
	UNITS "ms"
	MAX-ACCESS read-write
	STATUS current
	DESCRIPTION
		"TTS timer value."
	DEFVAL {500}
    ::= { asrConfig 6 }    
    
-- Audit-Timer configuration objects

auditTimerChannelLockout    OBJECT-TYPE
	SYNTAX Integer32(1..30)
	UNITS "minutes"
	MAX-ACCESS read-write
	STATUS current
	DESCRIPTION
		"Audit timer for channel lockout in minutes."
	DEFVAL {10}
	::= { auditTimerConfig 1 }

auditTimerHungCall    OBJECT-TYPE
	SYNTAX Integer32(0..120)
	UNITS "minutes"
	MAX-ACCESS read-write
	STATUS current
	DESCRIPTION
		"Audit timer for hung call in minutes."
	DEFVAL {5}
	::= { auditTimerConfig 2 }
	
auditTimerFax    OBJECT-TYPE
	SYNTAX Integer32(0..120)
	UNITS "minutes"
	MAX-ACCESS read-write
	STATUS current
	DESCRIPTION
		"Audit timer for fax in minutes."
	DEFVAL {5}
	::= { auditTimerConfig 3 }	

auditTimerHungChannel    OBJECT-TYPE
	SYNTAX Integer32(1..30)
	UNITS "minutes"
	MAX-ACCESS read-write
	STATUS current
	DESCRIPTION
		"Audit timer for hung channel in minutes."
	DEFVAL {10}
	::= { auditTimerConfig 4 }

auditTimerLongDurationConf    OBJECT-TYPE
	SYNTAX Integer32(1..2880)
	UNITS "minutes"
	MAX-ACCESS read-write
	STATUS current
	DESCRIPTION
		"Audit timer for long duration for Conference in minutes."
	DEFVAL {1440}
	::= { auditTimerConfig 5 }

auditTimerLongDurationIvr    OBJECT-TYPE
	SYNTAX Integer32(1..2880)
	UNITS "minutes"
	MAX-ACCESS read-write
	STATUS current
	DESCRIPTION
		"Audit timer for long duration for IVR in minutes."
	DEFVAL {60}
	::= { auditTimerConfig 6 }
	
auditTimerLongDurationFax    OBJECT-TYPE
	SYNTAX Integer32(1..2880)
	UNITS "minutes"
	MAX-ACCESS read-write
	STATUS current
	DESCRIPTION
		"Audit timer for long duration for FAX in minutes."
	DEFVAL {60}
	::= { auditTimerConfig 7 }	

auditTimerModule    OBJECT-TYPE
	SYNTAX Integer32(1..30)
	UNITS "minutes"
	MAX-ACCESS read-write
	STATUS current
	DESCRIPTION
		"Audit timer for Module in minutes."
	DEFVAL {10}
	::= { auditTimerConfig 8 }

-- Announcement-File configuration objects

ipUnityAnncFileType	OBJECT-TYPE
	SYNTAX INTEGER {
		system-based(1),
		application-based(2)
	}
	MAX-ACCESS read-write
	STATUS current
	DESCRIPTION
		"Type of Announcement to be added. This variable can not 
		be set alone. User needs to pass anncFilePath value also in 
		the same SET request. "
    ::= { ipUnityAnncConfig 1 }

ipUnityAnncFilePath	OBJECT-TYPE
	SYNTAX DisplayString
	MAX-ACCESS read-write
	STATUS current
	DESCRIPTION
		"Path and filename of the Announcement File to be added. This 
		variable can not be set alone. User needs to pass anncFileType 
		value also in the same SET request. "
    ::= { ipUnityAnncConfig 2 }

ipUnityAnncInstNextIndex		OBJECT-TYPE
	SYNTAX Integer32
	MAX-ACCESS read-only
	STATUS current
	DESCRIPTION
		"Identifies a hint for the next value of ipUnityAnncInstIndex to 
		be used in a row creation attempt for the ipUnityAnncInstTable. 
		If no new rows can be created, this object will have a value
		of -1."
	::= { ipUnityAnncConfig 3 }		

ipUnityAnncInstTable		OBJECT-TYPE
	SYNTAX SEQUENCE OF IpUnityAnncInstEntry
	MAX-ACCESS not-accessible
	STATUS current
	DESCRIPTION
		"The table is used for creating User Changes announcement instruction entries and  
                 viewing critical and permanent announcement instructions
		that are configured. Same table is also used to remove the announcement
		instructions, however user can only mark the entries to remove. Actual
		deletion happens when user does the save operation using ipUnityAnncInstCommand
	        when all the odsp banks are OutOfService.The entries in the user change can only
                be modified."
	::= { ipUnityAnncConfig 4 }

ipUnityAnncInstEntry  OBJECT-TYPE
    SYNTAX IpUnityAnncInstEntry
    MAX-ACCESS not-accessible
    STATUS current
    DESCRIPTION
		"An entry for announcement instruction."
    INDEX      { ipUnityAnncInstIndex }
    ::= { ipUnityAnncInstTable 1 }

IpUnityAnncInstEntry ::= SEQUENCE {
	ipUnityAnncInstIndex	        Integer32,
	ipUnityAnncInstSectionType	INTEGER,
	ipUnityAnncInstDesignation	INTEGER,
        ipUnityAnncInstType	        INTEGER,
        ipUnityAnncInstDynamicDownload  INTEGER, 
        ipUnityAnncInstAction           INTEGER, 
	ipUnityAnncInstPath	        DisplayString,
	ipUnityAnncInstLanguageOption1	LanguageBitMap,
	ipUnityAnncInstLanguageOption2	LanguageBitMap,
	ipUnityAnncInstLanguageOption3	LanguageBitMap,
	ipUnityAnncInstRowStatus	RowStatus
	}  

ipUnityAnncInstIndex	OBJECT-TYPE
	SYNTAX Integer32
	MAX-ACCESS not-accessible
	STATUS current
	DESCRIPTION
		"Index for this table."
    ::= { ipUnityAnncInstEntry 1 }

ipUnityAnncInstSectionType	OBJECT-TYPE
	SYNTAX INTEGER {
		critical (0),
		permanent (1),
                userChange (2)
	}
	MAX-ACCESS read-create
	STATUS current
	DESCRIPTION
		"Announcement instruction section type for this announcement instruction.This object
                 is used to indicate to the user as to which section the entry belongs to."
    ::= { ipUnityAnncInstEntry 2 }

ipUnityAnncInstDesignation	OBJECT-TYPE
	SYNTAX INTEGER {
		critical (0),
		permanent (1)
	}
	MAX-ACCESS read-create
	STATUS current
	DESCRIPTION
		"Announcement instruction designation." 
    ::= { ipUnityAnncInstEntry 3 }

ipUnityAnncInstType	OBJECT-TYPE
	SYNTAX INTEGER {
		system (0),
		application (1)
	}
	MAX-ACCESS read-create
	STATUS current
	DESCRIPTION
		"Announcement instruction type." 
    ::= { ipUnityAnncInstEntry 4 }    

ipUnityAnncInstDynamicDownload	OBJECT-TYPE
	SYNTAX INTEGER {
		off (0),
		on (1)
	}
	MAX-ACCESS read-create
	STATUS current
	DESCRIPTION
                  "Denotes whether the main directory is defined to be a 
                   dynamically downloadable path or not. Only PERMANENT 
                   announcement directories can be configured as 
                   dynamically downloadable."
    ::= { ipUnityAnncInstEntry 5 }    

ipUnityAnncInstAction	OBJECT-TYPE
	SYNTAX INTEGER {
		none (0),
		remove  (1),
		update  (2)
	}
	MAX-ACCESS read-create
	STATUS current
	DESCRIPTION
		"The row in the user config can be marked as remove. This row will be removed when save 
                 operation is done using anncInstCommand. Similarly the critical or permananet row can be marked as 
                 remove which will be removed in the similar way.
                 If user add or replace the audio files,  particular instruction entry needs to be reloaded by the bank. 
                 On setting the entry to update will reload the specified entry." 
    ::= { ipUnityAnncInstEntry 6 }    

ipUnityAnncInstPath	OBJECT-TYPE
	SYNTAX DisplayString 
	MAX-ACCESS read-create
	STATUS current
	DESCRIPTION
                "Root directory of inventory of announcements. Actual download can be from this directory or sub directories                  within this directory." 
    ::= { ipUnityAnncInstEntry 7 }    

ipUnityAnncInstLanguageOption1 OBJECT-TYPE
	SYNTAX LanguageBitMap 
	MAX-ACCESS read-create
	STATUS current
	DESCRIPTION
		"This identifies the languages to be downloaded.This value has to be compulsorily set."
    ::= { ipUnityAnncInstEntry 8 }    

ipUnityAnncInstLanguageOption2 OBJECT-TYPE
	SYNTAX LanguageBitMap 
	MAX-ACCESS read-create
	STATUS current
	DESCRIPTION
		"This identifies the languages to be downloaded. This object is optional and need not be set
                 along with the other objects."
    ::= { ipUnityAnncInstEntry 9 }    

ipUnityAnncInstLanguageOption3 OBJECT-TYPE
	SYNTAX LanguageBitMap 
	MAX-ACCESS read-create
	STATUS current
	DESCRIPTION
		"This identifies the languages to be downloaded.This object is optional and need not be set
		 along with the other objects."
    ::= { ipUnityAnncInstEntry 10 }    

ipUnityAnncInstRowStatus	OBJECT-TYPE
	SYNTAX RowStatus 
	MAX-ACCESS read-create
	STATUS current
	DESCRIPTION
		"The status of the row. Required to create or delete the entry in 
		this table. Only createAndGo method of row creation is supported 
		and createAndWait method is not supported. Actual
                deletion happens when user does the save operation using anncInstCommand."
    ::= { ipUnityAnncInstEntry 11 }    

ipUnityAnncInstFileNextIndex		OBJECT-TYPE
	SYNTAX Integer32
	MAX-ACCESS read-only
	STATUS current
	DESCRIPTION
		"Identifies a hint for the next value of anncInstFileIndex to 
		be used in a row creation attempt for the anncInstFileTable. 
		If no new rows can be created, this object will have a value
		of -1."
	::= { ipUnityAnncConfig 5 }		

ipUnityAnncInstFileTable		OBJECT-TYPE
	SYNTAX SEQUENCE OF IpUnityAnncInstFileEntry
	MAX-ACCESS not-accessible
	STATUS current
	DESCRIPTION
		"The table is used to add and delete the files in the User 
                 Changes announcement instruction entries. A file can be added or 
                deleted for those rows created in the annInstTable in the user 
                Config section."
	::= { ipUnityAnncConfig 6 }

ipUnityAnncInstFileEntry  OBJECT-TYPE
    SYNTAX IpUnityAnncInstFileEntry
    MAX-ACCESS not-accessible
    STATUS current
    DESCRIPTION
		"An entry for announcement instruction file."
    INDEX      { ipUnityAnncInstIndex,ipUnityAnncInstFileIndex }
    ::= { ipUnityAnncInstFileTable 1 }

IpUnityAnncInstFileEntry ::= SEQUENCE {
	ipUnityAnncInstFileIndex	Integer32,
	ipUnityAnncInstFileSectionType	INTEGER,
	ipUnityAnncInstFileName	        DisplayString,
	ipUnityAnncInstFileRowStatus	RowStatus
	}  

ipUnityAnncInstFileIndex	OBJECT-TYPE
	SYNTAX Integer32
	MAX-ACCESS not-accessible
	STATUS current
	DESCRIPTION
		"Index for this table."
    ::= { ipUnityAnncInstFileEntry 1 }

ipUnityAnncInstFileSectionType	OBJECT-TYPE
	SYNTAX INTEGER {
		critical (0),
		permanent (1),
                userChange (2)
	}
	MAX-ACCESS read-only
	STATUS current
	DESCRIPTION
		"Announcement instruction file section type for this announcement instruction.This object
                 is used to indicate to the user as to which section the file belongs to."
    ::= { ipUnityAnncInstFileEntry 2 }

ipUnityAnncInstFileName	OBJECT-TYPE
	SYNTAX DisplayString 
	MAX-ACCESS read-create
	STATUS current
	DESCRIPTION
                "The name of the audio file."
    ::= { ipUnityAnncInstFileEntry 3 }    

ipUnityAnncInstFileRowStatus	OBJECT-TYPE
	SYNTAX RowStatus 
	MAX-ACCESS read-create
	STATUS current
	DESCRIPTION
		"The status of the row. Required to create or delete the entry in 
		this table. Only createAndGo method of row creation is supported 
		and createAndWait method is not supported. Delete method will delete the file
                in the user changes section. Deleteion of files is not allowed if the
                entry is in critical or permanent section." 
    ::= { ipUnityAnncInstFileEntry 4 }    

ipUnityAnncInstCommand	OBJECT-TYPE
	SYNTAX INTEGER {
		save (1),
		cancel (2)
	} 
	MAX-ACCESS read-write
	STATUS current
	DESCRIPTION
	       "Command for announcement instructions
		save (1) - This applys to the announcement instructions created 
		           in the anncInstTable and anncInstFileTable. 
                           It also removes the entries for
		           critical and permanent announcement instructuion entries if they 
		           are marked as removed(1).
		cancel (2) - This  will remove all the user changes before the save command and also will 
                             change the critical or permanent entires marked as removed(1) to none(0)" 
    ::= { ipUnityAnncConfig 7 }

-- Electronic Surveillance (es) configuration objects
electronicSurveillance    OBJECT-TYPE
	SYNTAX Integer32(0..100)
	MAX-ACCESS read-write
	STATUS obsolete
	DESCRIPTION
		"Electronic Surveillance:  0 - 100."
	DEFVAL {0}
	::= { esConfig 1 }

-- File System configuration objects
fileSystemNextIndex OBJECT-TYPE
	SYNTAX Integer32(0..4 | -1)
	MAX-ACCESS read-only
	STATUS current
	DESCRIPTION
		"Identifies a hint for the next value of fileSystemIndex to 
		be used in a row creation attempt for the fileSystemTable. 
		If no new rows can be created, this object will have a value
		of -1."
	::= { fileSystemConfig 1 }
	
fileSystemTable		OBJECT-TYPE
	SYNTAX SEQUENCE OF FileSystemEntry         
	MAX-ACCESS not-accessible
	STATUS current
	DESCRIPTION
		"The table is used for configuring File System."
	::= { fileSystemConfig 2 }

fileSystemEntry  OBJECT-TYPE
	SYNTAX FileSystemEntry
    MAX-ACCESS not-accessible
    STATUS current
    DESCRIPTION
		"An entry for File System."
    INDEX      { fileSystemIndex }
    ::= { fileSystemTable 1 }

FileSystemEntry ::= SEQUENCE {
	fileSystemIndex			Integer32,
	fileSystemLocalDrvName	DisplayString,
	fileSystemAddr			DisplayString,
	fileSystemMount			DisplayString,
	fileSystemUserId		Integer32,
	fileSystemGroupId		Integer32,
	fileSystemAsrUsage		INTEGER,
	fileSystemRowStatus		RowStatus,
	fileSystemMountAlias		DisplayString,
	fileSystemRecoveryMethod	INTEGER
	}  

fileSystemIndex	OBJECT-TYPE
	SYNTAX Integer32(0..4)
	MAX-ACCESS not-accessible
	STATUS current
	DESCRIPTION
		"Index for this table."
    ::= { fileSystemEntry 1 } 

fileSystemLocalDrvName	OBJECT-TYPE
	SYNTAX DisplayString
	MAX-ACCESS read-only
	STATUS current
	DESCRIPTION
		"Local drive name for the file system entry."
    ::= { fileSystemEntry 2 }    

fileSystemAddr	OBJECT-TYPE
	SYNTAX DisplayString
	MAX-ACCESS read-create
	STATUS current
	DESCRIPTION
		"File System Address:  Hostname or IP Address."
    ::= { fileSystemEntry 3 }

fileSystemMount	OBJECT-TYPE
	SYNTAX DisplayString
	MAX-ACCESS read-create
	STATUS current
	DESCRIPTION
		"Mount Point of File System."
    ::= { fileSystemEntry 4 }

fileSystemUserId	OBJECT-TYPE
	SYNTAX Integer32(0..2147483647)
	MAX-ACCESS read-create
	STATUS current
	DESCRIPTION
		"User ID of File System."
    ::= { fileSystemEntry 5 }

fileSystemGroupId	OBJECT-TYPE
	SYNTAX Integer32(0..2147483647)
	MAX-ACCESS read-create
	STATUS current
	DESCRIPTION
		"Group ID of File System."
    ::= { fileSystemEntry 6 }

fileSystemAsrUsage	OBJECT-TYPE
	SYNTAX INTEGER {
		no(0),
		yes(1)
	}
	MAX-ACCESS read-create
	STATUS current
	DESCRIPTION
		"This File System can be used for ASR."
	DEFVAL	{no}
    ::= { fileSystemEntry 7 }

fileSystemRowStatus    OBJECT-TYPE
	SYNTAX RowStatus
	MAX-ACCESS read-create
	STATUS current
	DESCRIPTION
		"The status of the row. Required to create or delete the entry in 
		this table. Only createAndGo method of row creation is supported 
		and createAndWait method is not supported."
	::= { fileSystemEntry 8 }    
	            
fileSystemMountAlias	OBJECT-TYPE
	SYNTAX DisplayString
	MAX-ACCESS read-create
	STATUS current
	DESCRIPTION
		"File System Mount Alias."
    ::= { fileSystemEntry 9 }

fileSystemRecoveryMethod	OBJECT-TYPE
	SYNTAX INTEGER {
		macUpdate(0),
		remount(1)
	}
	MAX-ACCESS read-create
	STATUS current
	DESCRIPTION
		"This File System recovery method."
	DEFVAL	{macUpdate}
    ::= { fileSystemEntry 10 }

-- ICM-ASR configuration objects
engineDataTable		OBJECT-TYPE
	SYNTAX SEQUENCE OF EngineDataEntry
	MAX-ACCESS not-accessible
	STATUS current
	DESCRIPTION
		"The table is used for configuring ICM-ASR Engine data."
	::= { icmAsrConfig 1 }

engineDataEntry  OBJECT-TYPE
	SYNTAX EngineDataEntry
    MAX-ACCESS not-accessible
    STATUS current
    DESCRIPTION
		"An entry for ICM-ASR Engine Data."
    INDEX      { engineIndex }
    ::= { engineDataTable 1 }

EngineDataEntry ::= SEQUENCE {
	engineIndex			Integer32,
	engineNumber		Integer32,
	engineName			INTEGER,
	mrcpIPAddress		IpAddress,
	mrcpPort			Integer32,
	engineRowStatus		RowStatus
	}  

engineIndex	OBJECT-TYPE
	SYNTAX Integer32(0..31)
	MAX-ACCESS not-accessible
	STATUS current
	DESCRIPTION
		"Index for this table."
    ::= { engineDataEntry 1 }

engineNumber	OBJECT-TYPE
	SYNTAX Integer32 (5..2147483647)
	MAX-ACCESS read-create
	STATUS current
	DESCRIPTION
		"Engine Number:  5 and above."
    ::= { engineDataEntry 2 }

engineName	OBJECT-TYPE
	SYNTAX INTEGER {
		 nuance (1),
		 speechwork (2)
	}
	MAX-ACCESS read-create
	STATUS current
	DESCRIPTION
		"Engine Name."
    ::= { engineDataEntry 3 }

mrcpIPAddress	OBJECT-TYPE
	SYNTAX IpAddress
	MAX-ACCESS read-create
	STATUS current
	DESCRIPTION
		"MRCP IP Address."
    ::= { engineDataEntry 4 }

mrcpPort	OBJECT-TYPE
	SYNTAX Integer32(1025..65535)
	MAX-ACCESS read-create
	STATUS current
	DESCRIPTION
		"MRCP Port number."
    ::= { engineDataEntry 5 }

engineRowStatus    OBJECT-TYPE
	SYNTAX RowStatus
	MAX-ACCESS read-create
	STATUS current
	DESCRIPTION
		"The status of the row. Required to create or delete the entry in 
		this table. Only createAndGo method of row creation is supported 
		and createAndWait method is not supported."
	::= { engineDataEntry 6 }
	            
contextGroupTable		OBJECT-TYPE
	SYNTAX SEQUENCE OF ContextGroupEntry
	MAX-ACCESS not-accessible
	STATUS current
	DESCRIPTION
		"The table is used for configuring ICM-ASR Context Group."
	::= { icmAsrConfig 2 }

contextGroupEntry  OBJECT-TYPE
	SYNTAX ContextGroupEntry
    MAX-ACCESS not-accessible
    STATUS current
    DESCRIPTION
		"An entry for ICM-ASR Context Group."
    INDEX      { contextGroupIndex }
    ::= { contextGroupTable 1 }

ContextGroupEntry ::= SEQUENCE {
	contextGroupIndex		Integer32,
	contextGroupNumber		Integer32,
	contextEngineNumber			Integer32,
	contextVxmlRoot				DisplayString,
	contextGroupRowStatus	RowStatus
	}  

contextGroupIndex	OBJECT-TYPE
	SYNTAX Integer32(0..15)
	MAX-ACCESS not-accessible
	STATUS current
	DESCRIPTION
		"Index for this table."
    ::= { contextGroupEntry 1 }

contextGroupNumber	OBJECT-TYPE
	SYNTAX Integer32 (0..255)
	MAX-ACCESS read-create
	STATUS current
	DESCRIPTION
		"Context group Number:  0 to 255."
    ::= { contextGroupEntry 2 }

contextEngineNumber	OBJECT-TYPE
	SYNTAX Integer32 (5..2147483647)
	MAX-ACCESS read-create
	STATUS current
	DESCRIPTION
		"Engine Number:  5 and above."
    ::= { contextGroupEntry 3 }

contextVxmlRoot	OBJECT-TYPE
	SYNTAX DisplayString
	MAX-ACCESS read-create
	STATUS current
	DESCRIPTION
		"URL"
    ::= { contextGroupEntry 4 }

contextGroupRowStatus    OBJECT-TYPE
	SYNTAX RowStatus
	MAX-ACCESS read-create
	STATUS current
	DESCRIPTION
		"The status of the row. Required to create or delete the entry in 
		this table. Only createAndGo method of row creation is supported 
		and createAndWait method is not supported."
	::= { contextGroupEntry 5 }
	            
defaultContextGroup	OBJECT-TYPE
	SYNTAX Integer32 (0..255)
	MAX-ACCESS read-write
	STATUS current
	DESCRIPTION
		"Engine Number:  0 to 255."
    ::= { icmAsrConfig 3 }

icmAsrCommand	OBJECT-TYPE
	SYNTAX INTEGER {
		save (1)
	} 
	MAX-ACCESS read-write
	STATUS current
	DESCRIPTION
		"Command for saving icm-asr configuration"
    ::= { icmAsrConfig 4 }    

-- Emberdded variable configuration related objects

evTable	OBJECT-TYPE
	SYNTAX SEQUENCE OF EvEntry
	MAX-ACCESS not-accessible
	STATUS current
	DESCRIPTION
		"The table is used for viewing embedded variables
		that are configured. Same table is also used to remove the embedded
		variables, however user can only mark the entries to remove. Actual
		deletion happens when user does the save(1) operation using evCommand,
		when all the odsp banks are OutOfService."
	::= { evConfig 1 }

evEntry  OBJECT-TYPE
	SYNTAX EvEntry
    MAX-ACCESS not-accessible
    STATUS current
    DESCRIPTION
		"An entry for an embedded variable."
    INDEX      { evId }
    ::= { evTable 1 }

EvEntry ::= SEQUENCE {
	evId			DisplayString,
	evExpression	DisplayString,
	evMark			INTEGER
	}  

evId	OBJECT-TYPE
	SYNTAX DisplayString (SIZE (1..32))
	MAX-ACCESS not-accessible
	STATUS current
	DESCRIPTION
		"Index for this table."
    ::= { evEntry 1 }

evExpression	OBJECT-TYPE
	SYNTAX DisplayString
	MAX-ACCESS read-only
	STATUS current
	DESCRIPTION
		"Embedded variable expression."
    ::= { evEntry 2 }

evMark	OBJECT-TYPE
	SYNTAX INTEGER {
		active (1),
		toBeRemoved (2)
	}
	MAX-ACCESS read-write
	STATUS current
	DESCRIPTION
		"Marking for the embedded variable. User can mark it if
		he wish to remove this during next maintainnace window."
    ::= { evEntry 3 }    

userEvTable	OBJECT-TYPE
	SYNTAX SEQUENCE OF UserEvEntry
	MAX-ACCESS not-accessible
	STATUS current
	DESCRIPTION
		"This table is used to keep the embedded variable that
		can be saved during the maintanance. User can create the entries
		at any time but can be saved only when all the odsp banks are 
		OutOfServervice."
	::= { evConfig 2 }

userEvEntry  OBJECT-TYPE
	SYNTAX UserEvEntry
    MAX-ACCESS not-accessible
    STATUS current
    DESCRIPTION
		"An entry for an embedded variable."
    INDEX      { userEvId }
    ::= { userEvTable 1 }

UserEvEntry ::= SEQUENCE {
	userEvId			DisplayString,
	userEvExpression	DisplayString,
	userEvStatus		RowStatus
	}  

userEvId	OBJECT-TYPE
	SYNTAX DisplayString (SIZE (1..32))
	MAX-ACCESS not-accessible
	STATUS current
	DESCRIPTION
		"Index for this table."
    ::= { userEvEntry 1 }

userEvExpression	OBJECT-TYPE
	SYNTAX DisplayString
	MAX-ACCESS read-create
	STATUS current
	DESCRIPTION
		"Embedded variable expression."
    ::= { userEvEntry 2 }

userEvStatus	OBJECT-TYPE
	SYNTAX RowStatus
	MAX-ACCESS read-create
	STATUS current
	DESCRIPTION
		"The status of the row. Required to create or delete the entry in 
		this table. Only createAndGo method of row creation is supported 
		and createAndWait method is not supported."
    ::= { userEvEntry 3 }

evCommand	OBJECT-TYPE
	SYNTAX INTEGER {
		save (1),
		cancelDelete (2)
	} 
	MAX-ACCESS read-write
	STATUS current
	DESCRIPTION
		"Command for embedded variable
		
		save (1) - This applys the embedded variables created 
		           in the userEvTable. It also removes the entries from
		           evTable if they are marked as ToBeRemoved (2).
		           
		cancelDelete (2) - This marks the embedded variable that are
		                   marked as toBeRemoved (2) to active (1) in
		                   evTable"
    ::= { evConfig 3 }
    
-- Static-Route configuration objects

staticRouteNextIndex OBJECT-TYPE
	SYNTAX Integer32(0..9 | -1)
	MAX-ACCESS read-only
	STATUS current
	DESCRIPTION
		"Identifies a hint for the next value of staticRouteIndex to 
		be used in a row creation attempt for the staticRouteTable. 
		If no new rows can be created, this object will have a value
		of -1."
	::= { staticRouteConfig 1 }
	
staticRouteTable OBJECT-TYPE
	SYNTAX SEQUENCE OF StaticRouteEntry
	MAX-ACCESS not-accessible
	STATUS current
	DESCRIPTION
		"The table is used for configuring Static-Routers data."
	::= { staticRouteConfig 2 }

staticRouteEntry  OBJECT-TYPE
	SYNTAX StaticRouteEntry
    MAX-ACCESS not-accessible
    STATUS current
    DESCRIPTION
		"An entry for Static-Route Data."
    INDEX      { staticRouteIndex }
    ::= { staticRouteTable 1 }

StaticRouteEntry ::= SEQUENCE {
	staticRouteIndex		Integer32,
	networkId				IpAddress,
	subnetMask				IpAddress,
	routerAddress			IpAddress,
	tosPrecedence			Integer32,
	staticRouteStatus		RowStatus
	}  

staticRouteIndex	OBJECT-TYPE
	SYNTAX Integer32(0..9)
	MAX-ACCESS not-accessible
	STATUS current
	DESCRIPTION
		"Index for this table."
    ::= { staticRouteEntry 1 }
networkId	OBJECT-TYPE
	SYNTAX IpAddress
	MAX-ACCESS read-create
	STATUS current
	DESCRIPTION
		"Network ID of Static Route:  IP Address."
    ::= { staticRouteEntry 2 }

subnetMask	OBJECT-TYPE
	SYNTAX IpAddress
	MAX-ACCESS read-create
	STATUS current
	DESCRIPTION
		"Subnet Mask of Static Route"
    ::= { staticRouteEntry 3 }

routerAddress	OBJECT-TYPE
	SYNTAX IpAddress
	MAX-ACCESS read-create
	STATUS current
	DESCRIPTION
		"Router Address: IP Address."
    ::= { staticRouteEntry 4 }

tosPrecedence	OBJECT-TYPE
	SYNTAX Integer32(0..5)
	MAX-ACCESS read-create
	STATUS current
	DESCRIPTION
		"TOS Precedence:  0-5."
    ::= { staticRouteEntry 5 }

staticRouteStatus    OBJECT-TYPE
	SYNTAX RowStatus
	MAX-ACCESS read-create
	STATUS current
	DESCRIPTION
		"The status of the row. Required to create or delete the entry in 
		this table. Only createAndGo method of row creation is supported 
		and createAndWait method is not supported."
	::= { staticRouteEntry 6 }    

-- objects for netConfig group, ethernet and network configuration

ethernetTable		OBJECT-TYPE
	SYNTAX SEQUENCE OF EthernetEntry
	MAX-ACCESS not-accessible
	STATUS current
	DESCRIPTION
		"The table is used for configuring Ethernet interfaces
		for SCC cards."
	::= { netConfig 1 }

ethernetEntry  OBJECT-TYPE
	SYNTAX EthernetEntry
    MAX-ACCESS not-accessible
    STATUS current
    DESCRIPTION
		"An entry for each interface."
    INDEX { ethernetIfNum }
    ::= { ethernetTable 1 }

EthernetEntry ::= SEQUENCE {
	ethernetIfNum				Integer32,
	ethernetIfNetworkId			IpAddress,
	ethernetIfCard4IPAddress	IpAddress,
	ethernetIfCard5IPAddress	IpAddress,
	ethernetIfVIPAddress		IpAddress,		
	ethernetIfType    			SccIfType,
	ethernetRowStatus			RowStatus
	}  
	
ethernetIfNum	OBJECT-TYPE
	SYNTAX Integer32(0..7)
	MAX-ACCESS not-accessible
	STATUS current
	DESCRIPTION
		"Ethernet interface number in the SCC card."
    ::= { ethernetEntry 1 }
        
ethernetIfNetworkId	OBJECT-TYPE
	SYNTAX IpAddress
	MAX-ACCESS read-create
	STATUS current
	DESCRIPTION
		"Ethernet interface Network ID."
    ::= { ethernetEntry 2 }

ethernetIfCard4IPAddress	OBJECT-TYPE
	SYNTAX IpAddress
	MAX-ACCESS read-create
	STATUS current
	DESCRIPTION
		"Ethernet interface IP Address for card4."
    ::= { ethernetEntry 3 }
    
ethernetIfCard5IPAddress	OBJECT-TYPE
	SYNTAX IpAddress
	MAX-ACCESS read-create
	STATUS current
	DESCRIPTION
		"Ethernet interface IP Address for card5."
    ::= { ethernetEntry 4 }

ethernetIfVIPAddress	OBJECT-TYPE
	SYNTAX IpAddress
	MAX-ACCESS read-create
	STATUS current
	DESCRIPTION
		"Virtual IP Address for Ethernet interface."
    ::= { ethernetEntry 5 }        
    
ethernetIfType	OBJECT-TYPE
	SYNTAX SccIfType
	MAX-ACCESS read-create
	STATUS current
	DESCRIPTION
		"Interface type."
    ::= { ethernetEntry 6 }
    
ethernetRowStatus    OBJECT-TYPE
	SYNTAX RowStatus
	MAX-ACCESS read-create
	STATUS current
	DESCRIPTION
		"The status of the row. Required to create or delete the entry in 
		this table. Only createAndGo method of row creation is supported 
		and createAndWait method is not supported."
	::= { ethernetEntry 7 }             

networkTable		OBJECT-TYPE
	SYNTAX SEQUENCE OF NetworkEntry
	MAX-ACCESS not-accessible
	STATUS current
	DESCRIPTION
		"The table is used for configuring network information."
	::= { netConfig 2 }

networkEntry  OBJECT-TYPE
	SYNTAX NetworkEntry
    MAX-ACCESS not-accessible
    STATUS current
    DESCRIPTION
		"An entry for each network."
    INDEX { networkID }
    ::= { networkTable 1 }

NetworkEntry ::= SEQUENCE {
	networkID				IpAddress,
	networkSubnetMask		IpAddress,
	networkDefaultRouter	IpAddress,
	networkIRDPFlag			INTEGER,
	networkRowStatus		RowStatus
	}  
	
networkID	OBJECT-TYPE
	SYNTAX IpAddress
	MAX-ACCESS not-accessible
	STATUS current
	DESCRIPTION
		"Network ID."
    ::= { networkEntry 1 }

networkSubnetMask	OBJECT-TYPE
	SYNTAX IpAddress
	MAX-ACCESS read-create
	STATUS current
	DESCRIPTION
		"Subnet Mask."
    ::= { networkEntry 2 }
    
networkDefaultRouter	OBJECT-TYPE
	SYNTAX IpAddress
	MAX-ACCESS read-create
	STATUS current
	DESCRIPTION
		"IP Address of the default router."
    ::= { networkEntry 3 }
    
networkIRDPFlag	OBJECT-TYPE
	SYNTAX INTEGER {
		disable (0),
		enable (1)
	}
	MAX-ACCESS read-create
	STATUS current
	DESCRIPTION
		"Flag to enable IRDP."
    ::= { networkEntry 4 }
    
networkRowStatus    OBJECT-TYPE
	SYNTAX RowStatus
	MAX-ACCESS read-create
	STATUS current
	DESCRIPTION
		"The status of the row. Required to create or delete the entry in 
		this table. Only createAndGo method of row creation is supported 
		and createAndWait method is not supported."
	::= { networkEntry 5 } 
	
ipUnityIpv6EthernetTable		OBJECT-TYPE
	SYNTAX SEQUENCE OF IpunityIpv6EthernetEntry
	MAX-ACCESS not-accessible
	STATUS current
	DESCRIPTION
		"The table is used for configuring Ipv6 Ethernet interfaces
		for SCC cards."
	::= { netConfig 3 }

ipUnityIpv6EthernetEntry  OBJECT-TYPE
    SYNTAX IpunityIpv6EthernetEntry
    MAX-ACCESS not-accessible
    STATUS current
    DESCRIPTION
		"An entry for each interface."
    INDEX { ipUnityIpv6EthernetIfNum }
    ::= { ipUnityIpv6EthernetTable 1 }

IpunityIpv6EthernetEntry ::= SEQUENCE {
	ipUnityIpv6EthernetIfNum		Integer32,
	ipUnityIpv6EthernetPrefixLength		Integer32,
	ipUnityIpv6EthernetIfType    		IPv6SupportIfType,
	ipUnityIpv6EthernetIfCard4IPAddress	DisplayString,
	ipUnityIpv6EthernetIfCard5IPAddress	DisplayString,
	ipUnityIpv6EthernetIfVIPAddress		DisplayString,		
	ipUnityIpv6EthernetRowStatus		RowStatus
	}  
	
ipUnityIpv6EthernetIfNum	OBJECT-TYPE
	SYNTAX Integer32(0..7)
	MAX-ACCESS not-accessible
	STATUS current
	DESCRIPTION
		"Ethernet interface number in the SCC card."
    ::= { ipUnityIpv6EthernetEntry 1 }
        
ipUnityIpv6EthernetPrefixLength	OBJECT-TYPE
	SYNTAX Integer32(0..128)
	MAX-ACCESS read-create
	STATUS current
	DESCRIPTION
		"Prefix length."
    ::= { ipUnityIpv6EthernetEntry 2 }
        
ipUnityIpv6EthernetIfType	OBJECT-TYPE
	SYNTAX IPv6SupportIfType
	MAX-ACCESS read-create
	STATUS current
	DESCRIPTION
		"Interface type."
    ::= { ipUnityIpv6EthernetEntry 3 }
    
ipUnityIpv6EthernetIfCard4IPAddress	OBJECT-TYPE
	SYNTAX DisplayString
	MAX-ACCESS read-create
	STATUS current
	DESCRIPTION
		"Ethernet interface IPV6 Address for card4."
    ::= { ipUnityIpv6EthernetEntry 4 }
    
ipUnityIpv6EthernetIfCard5IPAddress	OBJECT-TYPE
	SYNTAX DisplayString
	MAX-ACCESS read-create
	STATUS current
	DESCRIPTION
		"Ethernet interface IPV6 Address for card5."
    ::= { ipUnityIpv6EthernetEntry 5 }

ipUnityIpv6EthernetIfVIPAddress	OBJECT-TYPE
	SYNTAX DisplayString
	MAX-ACCESS read-create
	STATUS current
	DESCRIPTION
		"Virtual IPV6 Address for Ethernet interface."
    ::= { ipUnityIpv6EthernetEntry 6 }        
    
ipUnityIpv6EthernetRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityIpv6EthernetEntry 7 }             

-- scc-cp configuration related objects

sccCpFlag OBJECT-TYPE
	SYNTAX INTEGER {
		disable (0),
		enable (1)
	}
	MAX-ACCESS read-write
	STATUS current
	DESCRIPTION
		"Flag to enable scc-cp."
    ::= { sccCpConfig 1 }

sccCpConfigTable		OBJECT-TYPE
	SYNTAX SEQUENCE OF SccCpConfigEntry
	MAX-ACCESS not-accessible
	STATUS current
	DESCRIPTION
		"The table is used for configuring scc cp network 
		information."
	::= { sccCpConfig 2 }

sccCpConfigEntry  OBJECT-TYPE
	SYNTAX SccCpConfigEntry
    MAX-ACCESS not-accessible
    STATUS current
    DESCRIPTION
		"An entry for sccCpConfigTable."
    INDEX { sccCpCardNum, sccCpBankNum }
    ::= { sccCpConfigTable 1 }

SccCpConfigEntry ::= SEQUENCE {
	sccCpCardNum		Integer32,
	sccCpBankNum		Integer32,
	sccCpNetworkID		IpAddress,
	sccCpSubnetMask		IpAddress,
	sccCpRouter			IpAddress,
	sccCpIpAddr			IpAddress,
	sccCpIRDPFlag		INTEGER,
	sccCpRowStatus		RowStatus
	}  
	
sccCpCardNum	OBJECT-TYPE
	SYNTAX Integer32 (0..3|6..9)
	MAX-ACCESS not-accessible
	STATUS current
	DESCRIPTION
		"Card number."
    ::= { sccCpConfigEntry 1 }
    
sccCpBankNum	OBJECT-TYPE
	SYNTAX Integer32 (0..3)
	MAX-ACCESS not-accessible
	STATUS current
	DESCRIPTION
		"Bank number."
    ::= { sccCpConfigEntry 2 } 
    	
sccCpNetworkID	OBJECT-TYPE
	SYNTAX IpAddress
	MAX-ACCESS read-create
	STATUS current
	DESCRIPTION
		"Network ID."
    ::= { sccCpConfigEntry 3 }

sccCpSubnetMask	OBJECT-TYPE
	SYNTAX IpAddress
	MAX-ACCESS read-create
	STATUS current
	DESCRIPTION
		"Subnet Mask."
    ::= { sccCpConfigEntry 4 }
    
sccCpRouter	OBJECT-TYPE
	SYNTAX IpAddress
	MAX-ACCESS read-create
	STATUS current
	DESCRIPTION
		"IP Address of the router."
    ::= { sccCpConfigEntry 5 }
    
sccCpIpAddr	OBJECT-TYPE
	SYNTAX IpAddress
	MAX-ACCESS read-create
	STATUS current
	DESCRIPTION
		"IP Address for sccCp."
    ::= { sccCpConfigEntry 6 }
    
sccCpIRDPFlag	OBJECT-TYPE
	SYNTAX INTEGER {
		disable (0),
		enable (1)
	}
	MAX-ACCESS read-create
	STATUS current
	DESCRIPTION
		"Flag to enable IRDP."
    ::= { sccCpConfigEntry 7 }
    
sccCpRowStatus    OBJECT-TYPE
	SYNTAX RowStatus
	MAX-ACCESS read-create
	STATUS current
	DESCRIPTION
		"The status of the row. Required to create or delete the entry in 
		this table. Only createAndGo method of row creation is supported 
		and createAndWait method is not supported."
	::= { sccCpConfigEntry 8 }    

sccCpVirtualIpAddr  OBJECT-TYPE
    SYNTAX IpAddress
    MAX-ACCESS read-create
    STATUS current
    DESCRIPTION
        "Virtual IP Address for sccCp."
    ::= { sccCpConfig 3 }

-- spm-G4 configuration related objects

spmG4ConfigTable OBJECT-TYPE
	SYNTAX SEQUENCE OF SpmG4ConfigEntry
	MAX-ACCESS not-accessible
	STATUS current
	DESCRIPTION
		"A table containing the list of SPM G4 configuration data."
	::= { spmG4Config 1 }

spmG4ConfigEntry OBJECT-TYPE
	SYNTAX SpmG4ConfigEntry
	MAX-ACCESS not-accessible
	STATUS current
	DESCRIPTION
		"An entry in the SPM G4 config table."
    INDEX { spmG4CardNum,
			spmG4BankNum,
			spmG4ModuleNum 
	}
	::= { spmG4ConfigTable  1 }

SpmG4ConfigEntry ::= SEQUENCE {
   spmG4CardNum		INTEGER,
   spmG4BankNum		INTEGER,
   spmG4ModuleNum	INTEGER,
   spmG4NetworkId	IpAddress,
   spmG4SubnetMask	IpAddress,
   spmG4RouterAddr	IpAddress,
   spmG4IpAddr		IpAddress,
   spmG4Application	INTEGER,
   spmG4RowStatus	RowStatus
   }

spmG4CardNum OBJECT-TYPE
	SYNTAX INTEGER (0..3 | 6..9)
	MAX-ACCESS not-accessible
	STATUS current
	DESCRIPTION
		"The card number of SPM card."
	::= { spmG4ConfigEntry 1 }
        
spmG4BankNum OBJECT-TYPE
	SYNTAX INTEGER (1|3)
	MAX-ACCESS not-accessible
	STATUS current
	DESCRIPTION
		"The bank number of SPM card."
	::= { spmG4ConfigEntry 2 }
        
spmG4ModuleNum OBJECT-TYPE
	SYNTAX INTEGER (0..1)
	MAX-ACCESS not-accessible
	STATUS current
	DESCRIPTION
		"The module number of the G4 in SPM card."
	::= { spmG4ConfigEntry 3 }
        
spmG4NetworkId OBJECT-TYPE
	SYNTAX IpAddress
	MAX-ACCESS read-create
	STATUS current
	DESCRIPTION
		"The network id of SPM G4."
	::= { spmG4ConfigEntry 4 }
        
spmG4SubnetMask OBJECT-TYPE
	SYNTAX IpAddress
	MAX-ACCESS read-create
	STATUS current
	DESCRIPTION
		"The subnet mask of SPM G4."
	::= { spmG4ConfigEntry 5 }
        
spmG4RouterAddr OBJECT-TYPE
	SYNTAX IpAddress
	MAX-ACCESS read-create
	STATUS current
	DESCRIPTION
		"The router address of SPM G4."
	::= { spmG4ConfigEntry 6 }
        
spmG4IpAddr OBJECT-TYPE
	SYNTAX IpAddress
	MAX-ACCESS read-create
	STATUS current
	DESCRIPTION
		"The IP Address of SPM G4."
	::= { spmG4ConfigEntry 7 }
        
spmG4Application OBJECT-TYPE
	SYNTAX INTEGER {
		asr (1),
		http (2),
 		vxml (3),
		scc-cp (4)
	}
	MAX-ACCESS read-create
	STATUS current
	DESCRIPTION
		"The Application type of SPM G4."
	::= { spmG4ConfigEntry 8 }
        
spmG4RowStatus OBJECT-TYPE
	SYNTAX RowStatus
	MAX-ACCESS read-create
	STATUS current
	DESCRIPTION
		"The status of the row."
	::= { spmG4ConfigEntry 9 }        

-- snmpConfig group objects
snmpNextManagerNum		OBJECT-TYPE
	SYNTAX Integer32(0..4 | -1)
	MAX-ACCESS read-only
	STATUS current
	DESCRIPTION
		"Identifies a hint for the next value of snmpManagerNum to 
		be used in a row creation attempt for the snmpManagerTable. 
		If no new rows can be created, this object will have a value
		of 0."
	::= { snmpConfig 1 }
	
snmpManagerTable		OBJECT-TYPE
	SYNTAX SEQUENCE OF SnmpManagerEntry
	MAX-ACCESS not-accessible
	STATUS current
	DESCRIPTION
		"The table is used for configuring SNMP Managers. This table serves
		as traps destination table. MediaServer sends all the SNMP traps to 
		configured SNMP Managers in this table."
	::= { snmpConfig 2 }

snmpManagerEntry  OBJECT-TYPE
	SYNTAX SnmpManagerEntry
    MAX-ACCESS not-accessible
    STATUS current
    DESCRIPTION
		"An entry for each SNMP Manager (trap destination)."
    INDEX { snmpManagerNum }
    ::= { snmpManagerTable 1 }

SnmpManagerEntry ::= SEQUENCE {
	snmpManagerNum			Integer32,
	snmpTrapDestAddress		DisplayString,
	snmpTrapPort			Integer32,
	snmpTrapCommunityString		DisplayString, 
	snmpManagerAccess		INTEGER,
	snmpManagerRowStatus	RowStatus
	}  
	
snmpManagerNum	OBJECT-TYPE
	SYNTAX Integer32(0..4)
	MAX-ACCESS not-accessible
	STATUS current
	DESCRIPTION
		"SNMP Manager number."
    ::= { snmpManagerEntry 1 }

snmpTrapDestAddress	OBJECT-TYPE
	SYNTAX DisplayString
	MAX-ACCESS read-create
	STATUS current
	DESCRIPTION
		"Hostname or the IP Address of the trap destination."
    ::= { snmpManagerEntry 2 }
    
snmpTrapPort OBJECT-TYPE
	SYNTAX Integer32(162 | 1025..65535)
	MAX-ACCESS read-create
	STATUS current
	DESCRIPTION
		"Port to send the SNMP traps for this manager. This object is not
		mandatory to create the row in this table. If value is not provided
		then 162 will be used as trap port."
	DEFVAL {162}
    ::= { snmpManagerEntry 3 }
    
snmpTrapCommunityString OBJECT-TYPE
	SYNTAX DisplayString (SIZE(1..32))
	MAX-ACCESS read-create
	STATUS current
	DESCRIPTION
		"Community string used in the trap message for this manager. This 
		object is not mandatory to create the row in this table. If value 
		is not provided then public will be used as trap community string."
	DEFVAL {"public"}
    ::= { snmpManagerEntry 4 }

snmpManagerAccess OBJECT-TYPE
	SYNTAX INTEGER {
	  trap (1),
	  set (2),
	  trapAndSet (3)
	}
	MAX-ACCESS read-create
	STATUS current
	DESCRIPTION
		"Access for this SNMP manager. If it is Trap then manager receives
		Traps and can perform get operation. If it TrapAndSet then manager
		can perform set operation. This is two restrict the number of
		SNMP managers that perform set operation and adds security in
		case of SNMPv2c."
	DEFVAL {1}
    ::= { snmpManagerEntry 5 }    

snmpManagerRowStatus    OBJECT-TYPE
	SYNTAX RowStatus
	MAX-ACCESS read-create
	STATUS current
	DESCRIPTION
		"The status of the row. Required to create or delete the entry in 
		this table. Only createAndGo method of row creation is supported 
		and createAndWait method is not supported."
	::= { snmpManagerEntry 6 }    
    
-- fax configuration related objects
	 
faxRate OBJECT-TYPE
	SYNTAX Integer32 ( 2400 | 4800 | 7200 | 9600 | 12000 | 14400)
	MAX-ACCESS read-write
	STATUS current
	DESCRIPTION
		"Used for configuring fax rate."
	::= { faxConfig 1 }

faxPayloadSize OBJECT-TYPE
	SYNTAX OCTET STRING (SIZE(1..3))
	MAX-ACCESS read-write
	STATUS current
	DESCRIPTION
		"Used for configuring fax payload size. Take upto three bytes and each 
                 byte takes decimal value of 10, 20 or 30. Same value can not be
                 repeasted. Some examples in decimal values of the bytes are
                 a) 10 b) 20 10 30 c) 20 30 d) 10 20 30
                
                 Same examples when represeneted in Hex
                 a) 0a b) 14 0a 1e c) 14 1e d) 0a 14 1e"
               
	DEFVAL {'14'h}
	::= { faxConfig 2 }	

	
--  call preservation configuration
	
ipUnityVxmlErrHandlerMode OBJECT-TYPE
	SYNTAX INTEGER {
		off (0),
		on (1)
	}
	MAX-ACCESS read-write
	STATUS current
	DESCRIPTION
		"The value corresponds to call preservation vxml Error handler mode. If mode is 1, then the url must not be empty."
	::= { ipUnityCallPreservConfig 1 }	

ipUnityVxmlErrHandlerURL OBJECT-TYPE
	SYNTAX DisplayString
	MAX-ACCESS read-write
	STATUS current
	DESCRIPTION
		"Default VXML error handler URL."
	::= { ipUnityCallPreservConfig 2 }	

ipUnityFailoverAnnounceMode OBJECT-TYPE
	SYNTAX INTEGER {
		off (0),
		on (1)
	}
	MAX-ACCESS read-write
	STATUS current
	DESCRIPTION
		"The value corresponds to call preservation failover announcement mode. If mode is 1, then the url must not be empty."
	::= { ipUnityCallPreservConfig 3 }	
	
ipUnityFailoverAnnounceUrl OBJECT-TYPE
	SYNTAX DisplayString
	MAX-ACCESS read-write
	STATUS current
	DESCRIPTION
		"The string corresponds to call preservation failover announcement URL."
	::= { ipUnityCallPreservConfig 4 }				

--  Conference configuration
	
ipUnitySpkrIdentification OBJECT-TYPE
	SYNTAX INTEGER {
		off (0),
		on (1)
	}
	MAX-ACCESS read-write
	STATUS current
	DESCRIPTION
		"The conference speaker id flag."
	::= { ipUnityConfConfig 1 }	

ipUnityLargeConference OBJECT-TYPE
	SYNTAX INTEGER {
		off (0),
		on (1)
	}
	MAX-ACCESS read-write
	STATUS current
	DESCRIPTION
		"Large conference flag."
	::= { ipUnityConfConfig 2 }

ipUnityConfToneSuppression OBJECT-TYPE
	SYNTAX INTEGER {
		off (0),
		on (1)
	}
	MAX-ACCESS read-write
	STATUS current
	DESCRIPTION
		"Conference tone suppression flag."
	::= { ipUnityConfConfig 3 }

-- Embedded Variable

ipUnityEmbeddedVarNextIndex		OBJECT-TYPE
	SYNTAX Integer32
	MAX-ACCESS read-only
	STATUS current
	DESCRIPTION
		"Identifies a hint for the next value of ipUnityEmbeddedVarIndex to 
		be used in a row creation attempt for the ipUnityEmbeddedVarTable. 
		If no new rows can be created, this object will have a value
		of -1."
	::= { ipUnityEmbeddedVarConfig 1 }		

ipUnityEmbeddedVarTable		OBJECT-TYPE
	SYNTAX SEQUENCE OF IpUnityEmbeddedVarEntry
	MAX-ACCESS not-accessible
	STATUS current
	DESCRIPTION
		"The table is used for creating change section entries and  
                 viewing commit section. Same table is also used to remove the entries,
		 however user can only mark the entries to remove. Actual
		 deletion happens when user does the save operation using ipUnityEmbeddedVarCommand."
	::= { ipUnityEmbeddedVarConfig 2 }

ipUnityEmbeddedVarEntry  OBJECT-TYPE
    SYNTAX IpUnityEmbeddedVarEntry
    MAX-ACCESS not-accessible
    STATUS current
    DESCRIPTION
		"An entry for Embedded variables."
    INDEX      { ipUnityEmbeddedVarIndex }
    ::= { ipUnityEmbeddedVarTable 1 }

IpUnityEmbeddedVarEntry ::= SEQUENCE {
	ipUnityEmbeddedVarIndex	        Integer32,
	ipUnityEmbeddedVarAction	INTEGER,
	ipUnityEmbeddedVarSectionType	INTEGER,
	ipUnityEmbeddedVarIdString      DisplayString,
	ipUnityEmbeddedVarExpString	DisplayString,
	ipUnityEmbeddedVarRowStatus	RowStatus
	}  

ipUnityEmbeddedVarIndex	OBJECT-TYPE
	SYNTAX Integer32
	MAX-ACCESS not-accessible
	STATUS current
	DESCRIPTION
		"Index for this table."
    ::= { ipUnityEmbeddedVarEntry 1 }

ipUnityEmbeddedVarAction	OBJECT-TYPE
	SYNTAX INTEGER {
		nothing (0),
		removed (1)
	}
	MAX-ACCESS read-create
	STATUS current
	DESCRIPTION
		"Embedded variable action value for this entry. This object
                 is used to delete the entry in the user changes."
    ::= { ipUnityEmbeddedVarEntry 2 }

ipUnityEmbeddedVarSectionType	OBJECT-TYPE
	SYNTAX INTEGER {
		commit (0),
		change (1)
	}
	MAX-ACCESS read-create
	STATUS current
	DESCRIPTION
		"Embedded variable section type for this entry. This object
                 is used to indicate to the user as to which section the entry belongs to."
    ::= { ipUnityEmbeddedVarEntry 3 }

ipUnityEmbeddedVarIdString	OBJECT-TYPE
	SYNTAX DisplayString (SIZE(1..100))
	MAX-ACCESS read-create
	STATUS current
	DESCRIPTION
		"Embedded variable ID string."
    ::= { ipUnityEmbeddedVarEntry 4 }

ipUnityEmbeddedVarExpString	OBJECT-TYPE
	SYNTAX DisplayString (SIZE(1..100))
	MAX-ACCESS read-create
	STATUS current
	DESCRIPTION
		"Embedded variable expression string."
    ::= { ipUnityEmbeddedVarEntry 5 }

ipUnityEmbeddedVarRowStatus	OBJECT-TYPE
	SYNTAX RowStatus 
	MAX-ACCESS read-create
	STATUS current
	DESCRIPTION
		"The status of the row. Required to create or delete the entry in 
		this table. Only createAndGo method of row creation is supported 
		and createAndWait method is not supported. Actual
                deletion happens when user does the save operation using ipUnityEmbeddedVarCommand."
    ::= { ipUnityEmbeddedVarEntry 6 }    

ipUnityEmbeddedVarCommand	OBJECT-TYPE
	SYNTAX INTEGER {
		save (1),
		cancel (2)
	} 
	MAX-ACCESS read-write
	STATUS current
	DESCRIPTION
	       "Command for Embedded variable,
		save (1) - This applys to the embeded variable created 
		           in the ipUnityEmbeddedVar table. It also removes the entries  
		           if they are marked as removed(1).
		cancel (2) - This  will remove all the user changes before the save command and also will 
                             chnage the commit section entires marked as removed(1) to none(0). " 
    ::= { ipUnityEmbeddedVarConfig 3 }

-- h248 
ipUnityH248Port  OBJECT-TYPE
	SYNTAX Integer32(1025..65535)
	MAX-ACCESS read-write
	STATUS current
	DESCRIPTION
		"h248 port value."
	DEFVAL {5246}                                  
	::= { ipUnityH248Config 1 }

ipUnityH248Retransmission  OBJECT-TYPE
	SYNTAX Integer32(0..65535)
	MAX-ACCESS read-write
	STATUS current
	DESCRIPTION
		"h248 retransmission value."
	::= { ipUnityH248Config 2 }

ipUnityH248TimerRequestTimeout  OBJECT-TYPE
	SYNTAX Integer32(30..120)
	MAX-ACCESS read-write
	STATUS current
	DESCRIPTION
		"Timeout value for h248 requests."
	DEFVAL {30}                                  
	::= { ipUnityH248Config 3 }
	
ipUnityH248TimerServiceChangeDelay OBJECT-TYPE
	SYNTAX Integer32(0..65535)
	MAX-ACCESS read-write
	STATUS current
	DESCRIPTION
		"Service change delay."
	DEFVAL {0}                                  
	::= { ipUnityH248Config 4 }	

ipUnityH248NormalMGExecutionTime OBJECT-TYPE
	SYNTAX Integer32(0..65535)
	MAX-ACCESS read-write
	STATUS current
	DESCRIPTION
		"Normal MG Execution Time."
	::= { ipUnityH248Config 5 }	

ipUnityH248NormalCallServerExecutionTime OBJECT-TYPE
	SYNTAX Integer32(0..65535)
	MAX-ACCESS read-write
	STATUS current
	DESCRIPTION
		"Normal Call Server Execution Time."
	::= { ipUnityH248Config 6 }	

ipUnityH248MGOriginatedPendingLimit OBJECT-TYPE
	SYNTAX Integer32(0..65535)
	MAX-ACCESS read-write
	STATUS current
	DESCRIPTION
		"MG Originated Pending Limit."
	::= { ipUnityH248Config 7 }	

ipUnityH248MRFCOriginatedPendingLimit OBJECT-TYPE
	SYNTAX Integer32(0..65535)
	MAX-ACCESS read-write
	STATUS current
	DESCRIPTION
		"MRFC Originated Pending Limit."
	::= { ipUnityH248Config 8 }	

ipUnityH248MGProvisionalResponseTimerValue OBJECT-TYPE
	SYNTAX Integer32(0..65535)
	MAX-ACCESS read-write
	STATUS current
	DESCRIPTION
		"MG Provisional Response Timer Value."
	::= { ipUnityH248Config 9 }	

ipUnityH248MRFCProvisionalResponseTimerValue OBJECT-TYPE
	SYNTAX Integer32(0..65535)
	MAX-ACCESS read-write
	STATUS current
	DESCRIPTION
		"MRFC Provisional Response Timer Value."
	::= { ipUnityH248Config 10 }	

-- h248 Call agent table
ipUnityH248CallAgentTable		OBJECT-TYPE
	SYNTAX SEQUENCE OF IpUnityH248CallAgentEntry
	MAX-ACCESS not-accessible
	STATUS current
	DESCRIPTION
		"The table is used for configuring H248 Call Agent information."
	::= { ipUnityH248Config 11 }

ipUnityH248CallAgentEntry  OBJECT-TYPE
	SYNTAX IpUnityH248CallAgentEntry
    MAX-ACCESS not-accessible
    STATUS current
    DESCRIPTION
		"An entry for H248 Call Agent."
    INDEX      { ipUnityH248CallAgentIndex }
    ::= { ipUnityH248CallAgentTable 1 }

IpUnityH248CallAgentEntry ::= SEQUENCE {
	ipUnityH248CallAgentIndex			Integer32,
	ipUnityH248CallAgentLocalName			DisplayString,
	ipUnityH248CallAgentHostName			DisplayString,
	ipUnityH248CallAgentPort                         Integer32,
        ipUnityH248CallAgentResourcePartition            Integer32,	
	ipUnityH248CallAgentRowStatus			RowStatus
	}  
	
ipUnityH248CallAgentIndex	OBJECT-TYPE
	SYNTAX Integer32(0..14)
	MAX-ACCESS not-accessible
	STATUS current
	DESCRIPTION
		"Call Agent number. Serves as index for this table."
    ::= { ipUnityH248CallAgentEntry 1 }

ipUnityH248CallAgentLocalName	OBJECT-TYPE
	SYNTAX DisplayString
	MAX-ACCESS read-create
	STATUS current
	DESCRIPTION
		"Name for Call Agent."
    ::= { ipUnityH248CallAgentEntry 2 }
    
ipUnityH248CallAgentHostName	OBJECT-TYPE
	SYNTAX DisplayString
	MAX-ACCESS read-create
	STATUS current
	DESCRIPTION
		"Host Name OR IP Address for Call Agent."
    ::= { ipUnityH248CallAgentEntry 3 }
    
ipUnityH248CallAgentPort	OBJECT-TYPE
	SYNTAX Integer32(1025..65535)
	MAX-ACCESS read-create
	STATUS current
	DESCRIPTION
		"Port number of the call agent." 
	DEFVAL {2944}                                  
    ::= { ipUnityH248CallAgentEntry 4 }
    
ipUnityH248CallAgentResourcePartition	OBJECT-TYPE
	SYNTAX Integer32(0..65535)
	MAX-ACCESS read-create
	STATUS current
	DESCRIPTION
		"Resource Partition value."
	DEFVAL {0}                                  
    ::= { ipUnityH248CallAgentEntry 5 }

ipUnityH248CallAgentRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityH248CallAgentEntry 6 }        

ipUnityH248RootMaxContext  OBJECT-TYPE
	SYNTAX Integer32(1..16384)
	MAX-ACCESS read-write
	STATUS current
	DESCRIPTION
		"Maximum number of contexts"
	DEFVAL {16384}
	::= { ipUnityH248Config 12 }

ipUnityH248RootMaxTerminationPerContext   OBJECT-TYPE
	SYNTAX Integer32(1..32)
	MAX-ACCESS read-write
	STATUS current
	DESCRIPTION
		"Maxiumum Termination per context."
	DEFVAL {32}
	::= { ipUnityH248Config 13 }

ipUnityH248Profile   OBJECT-TYPE
	SYNTAX DisplayString
	MAX-ACCESS read-write
	STATUS current
	DESCRIPTION
		"H248 Profile."
	::= { ipUnityH248Config 14 }

-- EndPoint Table
ipUnityEndPointTable		OBJECT-TYPE
	SYNTAX SEQUENCE OF IpUnityEndPointEntry
	MAX-ACCESS not-accessible
	STATUS current
	DESCRIPTION
		"The table is used for configuring End Point information."
	::= { ipUnityEndPointConfig 1 }

ipUnityEndPointEntry  OBJECT-TYPE
	SYNTAX IpUnityEndPointEntry
    MAX-ACCESS not-accessible
    STATUS current
    DESCRIPTION
		"An entry for End Point."
    INDEX      { ipUnityEndPointIndex, ipUnityEndPointType }
    ::= { ipUnityEndPointTable 1 }

IpUnityEndPointEntry ::= SEQUENCE {
	ipUnityEndPointIndex			Integer32,
	ipUnityEndPointType			INTEGER,
	ipUnityEndPointName			DisplayString,
	ipUnityEndPointValue			INTEGER,
	ipUnityEndPointRangeStart               Integer32,
	ipUnityEndPointRangeEnd                 Integer32,
	ipUnityEndPointRowStatus		RowStatus
	}  
	
ipUnityEndPointIndex	OBJECT-TYPE
	SYNTAX Integer32
	MAX-ACCESS not-accessible
	STATUS current
	DESCRIPTION
		"End Point number. Serves as index for this table."
    ::= { ipUnityEndPointEntry 1 }

ipUnityEndPointType	OBJECT-TYPE
	SYNTAX INTEGER {
		ivr(0),
		cnf(1),
		statConf(2),
		fax(3)
	}
	MAX-ACCESS not-accessible
	STATUS current
	DESCRIPTION
		"Endpoint type."
    ::= { ipUnityEndPointEntry 2 }
    
ipUnityEndPointName	OBJECT-TYPE
	SYNTAX DisplayString
	MAX-ACCESS read-create
	STATUS current
	DESCRIPTION
		"Name of the endpoint. It is must to create the entry in endpoint table." 
    ::= { ipUnityEndPointEntry 3 }
    
ipUnityEndPointValue	OBJECT-TYPE
	SYNTAX INTEGER {
		dynamic(1),
		static(2)
	}
	MAX-ACCESS read-create
	STATUS current
	DESCRIPTION
		"Endpoint value."
	DEFVAL {dynamic}                                  
    ::= { ipUnityEndPointEntry 4 }
    
ipUnityEndPointRangeStart	OBJECT-TYPE
	SYNTAX Integer32(1..6000)
	MAX-ACCESS read-create
	STATUS current
	DESCRIPTION
		"The starting range value."
    ::= { ipUnityEndPointEntry 5 }
    
ipUnityEndPointRangeEnd 	OBJECT-TYPE
	SYNTAX Integer32(1..6000)
	MAX-ACCESS read-create
	STATUS current
	DESCRIPTION
		"The end range value."
    ::= { ipUnityEndPointEntry 6 }
    
ipUnityEndPointRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityEndPointEntry 7 } 

-- Partition 
ipUnityPartitionHighUsageThreshold  OBJECT-TYPE
	SYNTAX Integer32(0..100)
	MAX-ACCESS read-write
	STATUS current
	DESCRIPTION
		"Partition high-usage threshold."
	::= { ipUnityPartitionConfig 1 }

ipUnityPartitionDeleteAll  OBJECT-TYPE
	SYNTAX INTEGER{
		yes(1)
	}
	MAX-ACCESS read-write
	STATUS current
	DESCRIPTION
		"Delete all partition."
	::= { ipUnityPartitionConfig 2 }

-- Partition table
ipUnityPartitionTable		OBJECT-TYPE
	SYNTAX SEQUENCE OF IpUnityPartitionEntry
	MAX-ACCESS not-accessible
	STATUS current
	DESCRIPTION
		"The table is used for configuring partition information."
	::= { ipUnityPartitionConfig 3 }

ipUnityPartitionEntry  OBJECT-TYPE
    SYNTAX IpUnityPartitionEntry
    MAX-ACCESS not-accessible
    STATUS current
    DESCRIPTION
		"An entry for partition."
    INDEX      { ipUnityPartitionIndex, ipUnityPartitionResourceType}  
    ::= { ipUnityPartitionTable 1 }

IpUnityPartitionEntry ::= SEQUENCE {
	ipUnityPartitionIndex			        Integer32,
	ipUnityPartitionResourceType		        INTEGER,
	ipUnityPartitionAllocation                      Integer32,
        ipUnityPartitionEnable                          INTEGER,	
	ipUnityPartitionRowStatus			RowStatus
	}  
	
ipUnityPartitionIndex	OBJECT-TYPE
	SYNTAX Integer32
	MAX-ACCESS not-accessible
	STATUS current
	DESCRIPTION
		"Partition number. Serves as index for this table."
    ::= { ipUnityPartitionEntry 1 }

ipUnityPartitionResourceType	OBJECT-TYPE
	SYNTAX INTEGER {
		ivr(0),
		cnf(1),
		cnfah(2),
		fax(3),
		vedio-ivr(4),
		vedio-conf(5)
	}
	MAX-ACCESS not-accessible
	STATUS current
	DESCRIPTION
		"Resource type."
    ::= { ipUnityPartitionEntry 2 }
    
ipUnityPartitionAllocation	OBJECT-TYPE
	SYNTAX Integer32(0..100)
	MAX-ACCESS read-create
	STATUS current
	DESCRIPTION
		"Percentage value for allocation."
    ::= { ipUnityPartitionEntry 3 }
    
ipUnityPartitionEnable	OBJECT-TYPE
	SYNTAX INTEGER {
		no(0),
		yes(1)
	}
	MAX-ACCESS read-create
	STATUS current
	DESCRIPTION
		"Resource enable."
    ::= { ipUnityPartitionEntry 4 }
    
ipUnityPartitionRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityPartitionEntry 5 }       

-- Video Image configuration 
ipUnityVideoImagePath OBJECT-TYPE
	SYNTAX DisplayString
	MAX-ACCESS read-write
	STATUS current
	DESCRIPTION
		"Video image path."
	::= { ipUnityVideoImageConfig 1 }
	
-- ICM configuration objects
ipUnityIcmContextGroupTable		OBJECT-TYPE
	SYNTAX SEQUENCE OF IpUnityIcmContextGroupEntry
	MAX-ACCESS not-accessible
	STATUS current
	DESCRIPTION
		"The table is used for configuring ICM Context Group."
	::= { ipUnityIcmConfig 1 }

ipUnityIcmContextGroupEntry  OBJECT-TYPE
    SYNTAX IpUnityIcmContextGroupEntry
    MAX-ACCESS not-accessible
    STATUS current
    DESCRIPTION
		"An entry for ICM Context Group."
    INDEX      { ipUnityIcmContextGroupIndex }
    ::= { ipUnityIcmContextGroupTable 1 }

IpUnityIcmContextGroupEntry ::= SEQUENCE {
	ipUnityIcmContextGroupIndex		Integer32,
	ipUnityIcmContextGroupNumber		Integer32,
	ipUnityIcmContextGroupType		INTEGER,
	ipUnityIcmContextGroupVendor            INTEGER,
	ipUnityIcmContextGroupRowStatus		RowStatus
	}  

ipUnityIcmContextGroupIndex	OBJECT-TYPE
	SYNTAX Integer32
	MAX-ACCESS not-accessible
	STATUS current
	DESCRIPTION
		"Index for this table."
    ::= { ipUnityIcmContextGroupEntry 1 }

ipUnityIcmContextGroupNumber	OBJECT-TYPE
	SYNTAX Integer32 (0..255)
	MAX-ACCESS read-create
	STATUS current
	DESCRIPTION
		"Context group Number:  0 to 255."
    ::= { ipUnityIcmContextGroupEntry 2 }

ipUnityIcmContextGroupType	OBJECT-TYPE
	SYNTAX INTEGER {
		 asr (1),
		 tts (2)
	}
	MAX-ACCESS read-create
	STATUS current
	DESCRIPTION
		"Context group type."
    ::= { ipUnityIcmContextGroupEntry 3 }

ipUnityIcmContextGroupVendor OBJECT-TYPE
	SYNTAX INTEGER {
		 speechwork (1),
		 speechify (2)
	}
	MAX-ACCESS read-create
	STATUS current
	DESCRIPTION
		"Context group vendor."
    ::= { ipUnityIcmContextGroupEntry 4 }

ipUnityIcmContextGroupRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityIcmContextGroupEntry 5 }
	            
ipUnityIcmEngineTable		OBJECT-TYPE
	SYNTAX SEQUENCE OF IpUnityEngineEntry
	MAX-ACCESS not-accessible
	STATUS current
	DESCRIPTION
		"The table is used for configuring ICM Engine data."
	::= { ipUnityIcmConfig 2 }

ipUnityIcmEngineEntry  OBJECT-TYPE
	SYNTAX IpUnityEngineEntry
    MAX-ACCESS not-accessible
    STATUS current
    DESCRIPTION
		"An entry for ICM Engine Data."
    INDEX      { ipUnityIcmEngineIndex }
    ::= { ipUnityIcmEngineTable 1 }

IpUnityEngineEntry ::= SEQUENCE {
	ipUnityIcmEngineIndex		Integer32,
	ipUnityGroupNumber		Integer32,
	ipUnityIcmEngineNumber		Integer32,
	ipUnityIcmEngineMrcpIPAddress	IpAddress,
	ipUnityIcmEngineMrcpPort		Integer32,
	ipUnityIcmEngineRowStatus		RowStatus
	}  

ipUnityIcmEngineIndex	OBJECT-TYPE
	SYNTAX Integer32(0..31)
	MAX-ACCESS not-accessible
	STATUS current
	DESCRIPTION
		"Index for this table."
    ::= { ipUnityIcmEngineEntry 1 }

ipUnityGroupNumber	OBJECT-TYPE
	SYNTAX Integer32 (0..255)
	MAX-ACCESS read-create
	STATUS current
	DESCRIPTION
		"Context group Number:  0 to 255."
    ::= { ipUnityIcmEngineEntry 2 }

ipUnityIcmEngineNumber	OBJECT-TYPE
	SYNTAX Integer32 (0..2147483647)
	MAX-ACCESS read-write
	STATUS current
	DESCRIPTION
		"Engine Number."
    ::= { ipUnityIcmEngineEntry 3 }

ipUnityIcmEngineMrcpIPAddress	OBJECT-TYPE
	SYNTAX IpAddress
	MAX-ACCESS read-create
	STATUS current
	DESCRIPTION
		"MRCP IP Address."
    ::= { ipUnityIcmEngineEntry 4 }

ipUnityIcmEngineMrcpPort	OBJECT-TYPE
	SYNTAX Integer32(1025..65535)
	MAX-ACCESS read-create
	STATUS current
	DESCRIPTION
		"MRCP Port number."
    ::= { ipUnityIcmEngineEntry 5 }

ipUnityIcmEngineRowStatus    OBJECT-TYPE
	SYNTAX RowStatus
	MAX-ACCESS read-create
	STATUS current
	DESCRIPTION
		"The status of the row. Required to create or delete the entry in 
		this table. Only createAndGo method of row creation is supported 
		and createAndWait method is not supported."
	::= { ipUnityIcmEngineEntry 6 }
	            
ipUnityIcmAsrDefaultContextGroup	OBJECT-TYPE
	SYNTAX Integer32 (0..255)
	MAX-ACCESS read-write
	STATUS current
	DESCRIPTION
		"ASR default context group."
    ::= { ipUnityIcmConfig 3 }

ipUnityIcmTtsDefaultContextGroup	OBJECT-TYPE
	SYNTAX Integer32 (0..255)
	MAX-ACCESS read-write
	STATUS current
	DESCRIPTION
		"TTS default context group."
    ::= { ipUnityIcmConfig 4 }

ipUnityIcmCommand	OBJECT-TYPE
	SYNTAX INTEGER {
		save (1)
	} 
	MAX-ACCESS read-write
	STATUS current
	DESCRIPTION
		"Command for saving icm configuration"
    ::= { ipUnityIcmConfig 5 }    

-- Priority Call resource reservation table
ipUnityPriorityCallTable		OBJECT-TYPE
	SYNTAX SEQUENCE OF IpUnityPriorityCallEntry
	MAX-ACCESS not-accessible
	STATUS current
	DESCRIPTION
		"The table is used for configuring priority call resource reservation."
	::= { ipUnityPriorityCallConfig 1 }

ipUnityPriorityCallEntry  OBJECT-TYPE
    SYNTAX IpUnityPriorityCallEntry
    MAX-ACCESS not-accessible
    STATUS current
    DESCRIPTION
		"An entry for priority."
    INDEX      { ipUnityPriorityCallResourceType}  
    ::= { ipUnityPriorityCallTable 1 }

IpUnityPriorityCallEntry ::= SEQUENCE {
	ipUnityPriorityCallResourceType		        INTEGER,
	ipUnityPriorityCallResourceUsage                Integer32
	}  
	
ipUnityPriorityCallResourceType	OBJECT-TYPE
	SYNTAX INTEGER {
		ivr(1),
		cnf(2),
		cnfah(3),
		fax(4),
                es (5),
		video-ivr(6),
		video-conf(7)
	}
	MAX-ACCESS not-accessible
	STATUS current
	DESCRIPTION
		"Resource type."
    ::= { ipUnityPriorityCallEntry 1 }
    
ipUnityPriorityCallResourceUsage	OBJECT-TYPE
	SYNTAX Integer32(0..2147483647)
	MAX-ACCESS read-create
	STATUS current
	DESCRIPTION
		"Priority resource usage."
    ::= { ipUnityPriorityCallEntry 2 }
   
--Dscp Configuration objects

dscpMedia    OBJECT-TYPE
       SYNTAX Integer32(0..63)
       MAX-ACCESS read-write
       STATUS current
       DESCRIPTION
               "dscp media value."
       DEFVAL {46}
   ::= { dscpConfig 1 }
 
dscpSignaling     OBJECT-TYPE
       SYNTAX Integer32(0..63)
       MAX-ACCESS read-write
       STATUS current
       DESCRIPTION
             "dscp Signaling value ."
       DEFVAL {10}
   ::= { dscpConfig 2 }

-- Electronic Surveillance (es) configuration objects
	
-- Media Server Security related configuration Objects

ike				OBJECT IDENTIFIER ::= { msSecurityObjects 1 }
ipsec			OBJECT IDENTIFIER ::= { msSecurityObjects 2 }
ssh				OBJECT IDENTIFIER ::= { msSecurityObjects 4 }
rtpTransform	OBJECT IDENTIFIER ::= { msSecurityObjects 5 }
rtcpTransform	OBJECT IDENTIFIER ::= { msSecurityObjects 6 }
ipUnityPortFilter	    OBJECT IDENTIFIER ::= { msSecurityObjects 7 } 

ikePolicyTable OBJECT-TYPE
	SYNTAX SEQUENCE OF IkePolicyEntry
	MAX-ACCESS not-accessible
	STATUS current
	DESCRIPTION
		"The table is used for configuring policies for ike."
	::= { ike 1 }

ikePolicyEntry OBJECT-TYPE
	SYNTAX IkePolicyEntry
    MAX-ACCESS not-accessible
    STATUS current
    DESCRIPTION
		"An entry for each ike policy."
    INDEX { ikePolicyIndex }
    ::= { ikePolicyTable 1 }

IkePolicyEntry ::= SEQUENCE {
	ikePolicyIndex				Integer32,
	ikePolicyIpsecAccessEntry	Integer32,
	ikePolicyAuthentication		INTEGER,
	ikePolicyProposal			Integer32,
	ikePolicyPreSharedString	DisplayString,
	ikePolicyNum				Integer32,
	ikePolicyRowStatus			RowStatus
	}  
	
ikePolicyIndex OBJECT-TYPE
	SYNTAX Integer32(0..15)
	MAX-ACCESS not-accessible
	STATUS current
	DESCRIPTION
		"Serves as index for this table."
    ::= { ikePolicyEntry 1 }

ikePolicyIpsecAccessEntry OBJECT-TYPE
	SYNTAX Integer32(0..255)
	MAX-ACCESS read-create
	STATUS current
	DESCRIPTION
		"ipsec access entry value."
    ::= { ikePolicyEntry 2 }
    
ikePolicyAuthentication OBJECT-TYPE
	SYNTAX INTEGER {
		preshared (1),
		signature (2)
	}
	MAX-ACCESS read-create
	STATUS current
	DESCRIPTION
		"ike authentication type."
    ::= { ikePolicyEntry 3 }
    
ikePolicyProposal OBJECT-TYPE
	SYNTAX Integer32(0..255)
	MAX-ACCESS read-create
	STATUS current
	DESCRIPTION
		"Proposal number corresponds to this policy."
    ::= { ikePolicyEntry 4 }
    
ikePolicyPreSharedString OBJECT-TYPE
	SYNTAX DisplayString
	MAX-ACCESS read-create
	STATUS current
	DESCRIPTION
		"Pre shared string for this policy."
    ::= { ikePolicyEntry 5 }

ikePolicyNum OBJECT-TYPE
	SYNTAX Integer32(0..255)
	MAX-ACCESS read-only
	STATUS current
	DESCRIPTION
		"Policy number. This is not used to create the entry but can be
		read once policy is created."
    ::= { ikePolicyEntry 6 }
    
ikePolicyRowStatus OBJECT-TYPE
	SYNTAX RowStatus
	MAX-ACCESS read-create
	STATUS current
	DESCRIPTION
		"The status of the row. Required to create or delete the entry in 
		this table. Only createAndGo method of row creation is supported 
		and createAndWait method is not supported."
	::= { ikePolicyEntry 7 }             

ikeProposalTable OBJECT-TYPE
	SYNTAX SEQUENCE OF IkeProposalEntry
	MAX-ACCESS not-accessible
	STATUS current
	DESCRIPTION
		"The table is used for configuring proposal(s) for ike."
	::= { ike 2 }

ikeProposalEntry OBJECT-TYPE
	SYNTAX IkeProposalEntry
    MAX-ACCESS not-accessible
    STATUS current
    DESCRIPTION
		"An entry for each ike proposal."
    INDEX { ikeProposalIndex }
    ::= { ikeProposalTable 1 }

IkeProposalEntry ::= SEQUENCE {
	ikeProposalIndex			Integer32,
	ikeProposalTransform		Integer32,
	ikeProposalDHGroup			INTEGER,
	ikeProposalLifetimeKbytes	Integer32,
	ikeProposalLifetimeSec		Integer32,
	ikeProposalNum				Integer32,
	ikeProposalRowStatus		RowStatus
	}  
	
ikeProposalIndex OBJECT-TYPE
	SYNTAX Integer32(0..15)
	MAX-ACCESS not-accessible
	STATUS current
	DESCRIPTION
		"Serves as index for this table."
    ::= { ikeProposalEntry 1 }

ikeProposalTransform OBJECT-TYPE
	SYNTAX Integer32(0..255)
	MAX-ACCESS read-create
	STATUS current
	DESCRIPTION
		"."
    ::= { ikeProposalEntry 2 }
    
ikeProposalDHGroup OBJECT-TYPE
	SYNTAX INTEGER {
		dh-group1 (1),
		dh-group2 (2)
	}
	MAX-ACCESS read-create
	STATUS current
	DESCRIPTION
		"."
    ::= { ikeProposalEntry 3 }
    
ikeProposalLifetimeKbytes OBJECT-TYPE
	SYNTAX Integer32(0..65535)
	MAX-ACCESS read-create
	STATUS current
	DESCRIPTION
		"."
    ::= { ikeProposalEntry 4 }
    
ikeProposalLifetimeSec OBJECT-TYPE
	SYNTAX Integer32(0..65535)
	MAX-ACCESS read-create
	STATUS current
	DESCRIPTION
		"."
    ::= { ikeProposalEntry 5 }

ikeProposalNum OBJECT-TYPE
	SYNTAX Integer32(0..255)
	MAX-ACCESS read-only
	STATUS current
	DESCRIPTION
		"Proposal number. This is not used to create the entry but can be
		read once policy is created."
    ::= { ikeProposalEntry 6 }
    
ikeProposalRowStatus OBJECT-TYPE
	SYNTAX RowStatus
	MAX-ACCESS read-create
	STATUS current
	DESCRIPTION
		"The status of the row. Required to create or delete the entry in 
		this table. Only createAndGo method of row creation is supported 
		and createAndWait method is not supported."
	::= { ikeProposalEntry 7 }             

ikeTransformTable OBJECT-TYPE
	SYNTAX SEQUENCE OF IkeTransformEntry
	MAX-ACCESS not-accessible
	STATUS current
	DESCRIPTION
		"The table is used for configuring Transform for ike."
	::= { ike 3 }

ikeTransformEntry OBJECT-TYPE
	SYNTAX IkeTransformEntry
    MAX-ACCESS not-accessible
    STATUS current
    DESCRIPTION
		"An entry for each ike Transform."
    INDEX { ikeTransformIndex }
    ::= { ikeTransformTable 1 }

IkeTransformEntry ::= SEQUENCE {
	ikeTransformIndex			Integer32,
	ikeTransformEncryption		INTEGER,
	ikeTransformAuthentication	INTEGER,
	ikeTransformNum				Integer32,
	ikeTransformRowStatus		RowStatus
	}  
	
ikeTransformIndex OBJECT-TYPE
	SYNTAX Integer32(0..15)
	MAX-ACCESS not-accessible
	STATUS current
	DESCRIPTION
		"Serves as index for this table."
    ::= { ikeTransformEntry 1 }

ikeTransformEncryption OBJECT-TYPE
	SYNTAX INTEGER {
		des (1),
		des3 (2)
	}
	MAX-ACCESS read-create
	STATUS current
	DESCRIPTION
		"."
    ::= { ikeTransformEntry 2 }
    
ikeTransformAuthentication OBJECT-TYPE
	SYNTAX INTEGER {
		md5 (1),
		sha (2)
	}
	MAX-ACCESS read-create
	STATUS current
	DESCRIPTION
		"."
    ::= { ikeTransformEntry 3 }
        
ikeTransformNum OBJECT-TYPE
	SYNTAX Integer32(0..255)
	MAX-ACCESS read-only
	STATUS current
	DESCRIPTION
		"."
    ::= { ikeTransformEntry 4 }
    
ikeTransformRowStatus OBJECT-TYPE
	SYNTAX RowStatus
	MAX-ACCESS read-create
	STATUS current
	DESCRIPTION
		"The status of the row. Required to create or delete the entry in 
		this table. Only createAndGo method of row creation is supported 
		and createAndWait method is not supported."
	::= { ikeTransformEntry 5 }             

-- ipsec related security objects

ipSecAccessTable		OBJECT-TYPE
	SYNTAX SEQUENCE OF IPSecAccessEntry
	MAX-ACCESS not-accessible
	STATUS current
	DESCRIPTION
		"The table is used for configuring IP Sec Access Entry data."
	::= { ipsec 1 }

ipSecAccessEntry  OBJECT-TYPE
	SYNTAX IPSecAccessEntry
    MAX-ACCESS not-accessible
    STATUS current
    DESCRIPTION
		"An entry for IP Sec Access Entry Data."
    INDEX      { ipSecAccessIndex }
    ::= { ipSecAccessTable 1 }

IPSecAccessEntry ::= SEQUENCE {
	ipSecAccessIndex		Integer32,
	peerRemote				IpAddress,
	peerLocal				IpAddress,
	accessEntryNumber		Integer32,
	ipSecAccessRowStatus	RowStatus,
        byPassPolicy	INTEGER
	}  

ipSecAccessIndex	OBJECT-TYPE
	SYNTAX Integer32(0..15)
	MAX-ACCESS not-accessible
	STATUS current
	DESCRIPTION
		"Index for this table."
    ::= { ipSecAccessEntry 1 }

peerRemote	OBJECT-TYPE
	SYNTAX IpAddress
	MAX-ACCESS read-create
	STATUS current
	DESCRIPTION
		"IP Address of a Peer-Remote of an IP Sec Access Entry."
    ::= { ipSecAccessEntry 2 }

peerLocal	OBJECT-TYPE
	SYNTAX IpAddress
	MAX-ACCESS read-create
	STATUS current
	DESCRIPTION
		"IP Address of a Peer-Local of an IP Sec Access Entry."
    ::= { ipSecAccessEntry 3 }

accessEntryNumber	OBJECT-TYPE
	SYNTAX Integer32 (0..255)
	MAX-ACCESS read-only
	STATUS current
	DESCRIPTION
		"IP Sec Access Entry Number."
    ::= { ipSecAccessEntry 4 }

ipSecAccessRowStatus    OBJECT-TYPE
	SYNTAX RowStatus
	MAX-ACCESS read-create
	STATUS current
	DESCRIPTION
		"The status of the row. Required to create or delete the entry in 
		this table. Only createAndGo method of row creation is supported 
		and createAndWait method is not supported."
	::= { ipSecAccessEntry 5 }

byPassPolicy	OBJECT-TYPE
	SYNTAX INTEGER {
               off (0),
               on (1)
        }
	MAX-ACCESS read-create
	STATUS current
	DESCRIPTION
		"Bypass Policy for this ipSecAccess Entry. This is not required to 
                create the acess entry, but can be configured later."
        ::= { ipSecAccessEntry 6 }

-- IP Sec Policy table
ipSecPolicyTable		OBJECT-TYPE
	SYNTAX SEQUENCE OF IPSecPolicyEntry
	MAX-ACCESS not-accessible
	STATUS current
	DESCRIPTION
		"The table is used for configuring IP Sec Policy data."
	::= { ipsec 4 }

ipSecPolicyEntry  OBJECT-TYPE
	SYNTAX IPSecPolicyEntry
    MAX-ACCESS not-accessible
    STATUS current
    DESCRIPTION
		"An entry for IP Sec Policy Data."
    INDEX      { ipSecPolicyIndex }
    ::= { ipSecPolicyTable 1 }

IPSecPolicyEntry ::= SEQUENCE {
	ipSecPolicyIndex		Integer32,
	ipSecAccessEntryNumber	Integer32,
	proposal1				Integer32,
	proposal2				Integer32,
	proposal3				Integer32,
	proposal4				Integer32,
	policyNumber			Integer32,
	ipSecPolicyRowStatus	RowStatus
	}  

ipSecPolicyIndex	OBJECT-TYPE
	SYNTAX Integer32(0..15)
	MAX-ACCESS not-accessible
	STATUS current
	DESCRIPTION
		"Index for this table."
    ::= { ipSecPolicyEntry 1 }

ipSecAccessEntryNumber	OBJECT-TYPE
	SYNTAX Integer32 (0..255)
	MAX-ACCESS read-create
	STATUS current
	DESCRIPTION
		"IP Sec Access Entry given back from configuring IP Sec Access-entry."
    ::= { ipSecPolicyEntry 2 }

proposal1	OBJECT-TYPE
	SYNTAX Integer32 (0..255)
	MAX-ACCESS read-create
	STATUS current
	DESCRIPTION
		"Proposal Number given back when configuring IPSec Proposal."
    ::= { ipSecPolicyEntry 3 }

proposal2	OBJECT-TYPE
	SYNTAX Integer32 (0..255)
	MAX-ACCESS read-create
	STATUS current
	DESCRIPTION
		"Proposal Number given back when configuring IPSec Proposal."
    ::= { ipSecPolicyEntry 4 }

proposal3	OBJECT-TYPE
	SYNTAX Integer32 (0..255)
	MAX-ACCESS read-create
	STATUS current
	DESCRIPTION
		"Proposal Number given back when configuring IPSec Proposal."
    ::= { ipSecPolicyEntry 5 }

proposal4	OBJECT-TYPE
	SYNTAX Integer32 (0..255)
	MAX-ACCESS read-create
	STATUS current
	DESCRIPTION
		"Proposal Number given back when configuring IPSec Proposal."
    ::= { ipSecPolicyEntry 6 }

policyNumber	OBJECT-TYPE
	SYNTAX Integer32 (0..255)
	MAX-ACCESS read-only
	STATUS current
	DESCRIPTION
		"Policy Number for IP Sec Policy."
    ::= { ipSecPolicyEntry 7 }

ipSecPolicyRowStatus    OBJECT-TYPE
	SYNTAX RowStatus
	MAX-ACCESS read-create
	STATUS current
	DESCRIPTION
		"The status of the row. Required to create or delete the entry in 
		this table. Only createAndGo method of row creation is supported 
		and createAndWait method is not supported."
	::= { ipSecPolicyEntry 8 }

-- IP Sec Proposal table
ipSecProposalTable		OBJECT-TYPE
	SYNTAX SEQUENCE OF IPSecProposalEntry
	MAX-ACCESS not-accessible
	STATUS current
	DESCRIPTION
		"The table is used for configuring IP Sec Proposal data."
	::= { ipsec 5 }

ipSecProposalEntry  OBJECT-TYPE
	SYNTAX IPSecProposalEntry
    MAX-ACCESS not-accessible
    STATUS current
    DESCRIPTION
		"An entry for IP Sec Proposal Data."
    INDEX      { ipSecProposalIndex }
    ::= { ipSecProposalTable 1 }

IPSecProposalEntry ::= SEQUENCE {
	ipSecProposalIndex		Integer32,
	transformNumber			Integer32,
	diffieHellmanGroup		INTEGER,
	antiReplay				INTEGER,
	ipSecMode				INTEGER,
	lifetimeKilobytes		Integer32,
	lifetimeSeconds			Integer32,
	proposalNumber			Integer32,
	ipSecProposalRowStatus	RowStatus
	}  

ipSecProposalIndex	OBJECT-TYPE
	SYNTAX Integer32(0..15)
	MAX-ACCESS not-accessible
	STATUS current
	DESCRIPTION
		"Index for this table."
    ::= { ipSecProposalEntry 1 }

transformNumber	OBJECT-TYPE
	SYNTAX Integer32 (0..255)
	MAX-ACCESS read-create
	STATUS current
	DESCRIPTION
		"IP Sec Transform Number given back from configuring IP Sec Transform."
    ::= { ipSecProposalEntry 2 }

diffieHellmanGroup	OBJECT-TYPE
	SYNTAX INTEGER {
		dh-group1 (1),
		dh-group2 (2)
	}
	MAX-ACCESS read-create
	STATUS current
	DESCRIPTION
		"Diffie-Hellman Group number:  dh-group1 or dh-group2."
	DEFVAL {dh-group1}
    ::= { ipSecProposalEntry 3 }

antiReplay	OBJECT-TYPE
	SYNTAX INTEGER {
		off (0),
		on (1)
	}
	MAX-ACCESS read-create
	STATUS current
	DESCRIPTION
		"Anti-replay:  off or on.  Initially defaults to off."
	DEFVAL {off}
    ::= { ipSecProposalEntry 4 }

ipSecMode	OBJECT-TYPE
	SYNTAX INTEGER {
		transport-mode (2)
	}
	MAX-ACCESS read-create
	STATUS current
	DESCRIPTION
		"Mode - transport-mode."
    ::= { ipSecProposalEntry 5 }

lifetimeKilobytes	OBJECT-TYPE
	SYNTAX Integer32 (0..65535)
	UNITS "kilobytes"
	MAX-ACCESS read-create
	STATUS current
	DESCRIPTION
		"Lifetime in Kilobytes:  initially defaults 256kb."
	DEFVAL {256}
    ::= { ipSecProposalEntry 6 }

lifetimeSeconds	OBJECT-TYPE
	SYNTAX Integer32 (0..65535)
	UNITS "seconds"
	MAX-ACCESS read-create
	STATUS current
	DESCRIPTION
		"Lifetime in Seconds:  initially defaults 3600sec."
	DEFVAL {3600}
    ::= { ipSecProposalEntry 7 }

proposalNumber	OBJECT-TYPE
	SYNTAX Integer32 (0..255)
	MAX-ACCESS read-only
	STATUS current
	DESCRIPTION
		"Proposal Number for IP Sec Proposal."
    ::= { ipSecProposalEntry 8 }

ipSecProposalRowStatus    OBJECT-TYPE
	SYNTAX RowStatus
	MAX-ACCESS read-create
	STATUS current
	DESCRIPTION
		"The status of the row. Required to create or delete the entry in 
		this table. Only createAndGo method of row creation is supported 
		and createAndWait method is not supported."
	::= { ipSecProposalEntry 9 }

-- IP Sec Transform table
ipSecTransformTable		OBJECT-TYPE
	SYNTAX SEQUENCE OF IPSecTransformEntry
	MAX-ACCESS not-accessible
	STATUS current
	DESCRIPTION
		"The table is used for configuring IP Sec Transform data."
	::= { ipsec 6 }

ipSecTransformEntry  OBJECT-TYPE
	SYNTAX IPSecTransformEntry
    MAX-ACCESS not-accessible
    STATUS current
    DESCRIPTION
		"An entry for IP Sec Transform Data."
    INDEX      { ipSecTransformIndex }
    ::= { ipSecTransformTable 1 }

IPSecTransformEntry ::= SEQUENCE {
	ipSecTransformIndex		Integer32,
	encryption				INTEGER,
	authentication			INTEGER,
	protocol				INTEGER,
	ipSecTransformNumber			Integer32,
	ipSecTransformRowStatus	RowStatus
	}  

ipSecTransformIndex	OBJECT-TYPE
	SYNTAX Integer32(0..6)
	MAX-ACCESS not-accessible
	STATUS current
	DESCRIPTION
		"Index for this table."
    ::= { ipSecTransformEntry 1 }

encryption	OBJECT-TYPE
	SYNTAX INTEGER {
		des (2),
		des3 (3),
		null (11)
	}
	MAX-ACCESS read-create
	STATUS current
	DESCRIPTION
		"IP Sec Transform encryption:  des, des3, null"
    ::= { ipSecTransformEntry 2 }

authentication	OBJECT-TYPE
	SYNTAX INTEGER {
		md5 (1),
		sha (2)
	}
	MAX-ACCESS read-create
	STATUS current
	DESCRIPTION
		"IP Sec Transform authentication:  md5 or sha."
	::= { ipSecTransformEntry 3 }

protocol	OBJECT-TYPE
	SYNTAX INTEGER {
		esp (1)
	}
	MAX-ACCESS read-create
	STATUS current
	DESCRIPTION
		"IP Sec Transform protocol - esp."
    ::= { ipSecTransformEntry 4 }

ipSecTransformNumber	OBJECT-TYPE
	SYNTAX Integer32 (0..255)
	MAX-ACCESS read-only
	STATUS current
	DESCRIPTION
		"Transform Number for IP Sec Transform."
    ::= { ipSecTransformEntry 5 }

ipSecTransformRowStatus    OBJECT-TYPE
	SYNTAX RowStatus
	MAX-ACCESS read-create
	STATUS current
	DESCRIPTION
		"The status of the row. Required to create or delete the entry in 
		this table. Only createAndGo method of row creation is supported 
		and createAndWait method is not supported."
	::= { ipSecTransformEntry 6 }


-- IP Sec Ethernet Interface Mode table
ipSecEtherModeTable      OBJECT-TYPE
    SYNTAX SEQUENCE OF IPSecEtherModeEntry
    MAX-ACCESS not-accessible
    STATUS current
    DESCRIPTION
        "The table is used for configuring IP Sec Ethernet Interface Mode."
    ::= { ipsec 7 }

ipSecEtherModeEntry  OBJECT-TYPE
    SYNTAX IPSecEtherModeEntry
    MAX-ACCESS not-accessible
    STATUS current
    DESCRIPTION
        "An entry for IP Sec Ethernet Interface Mode. One entry per card
         and per interface."
    INDEX      { etherInterface }
    ::= { ipSecEtherModeTable 1 }

IPSecEtherModeEntry ::= SEQUENCE {
    etherInterface           Integer32,
    etherMode                        INTEGER
    }
   
etherInterface   OBJECT-TYPE
    SYNTAX Integer32 (0..7)
    MAX-ACCESS not-accessible
    STATUS current
    DESCRIPTION
        "Ethernet Interface number to set the Mode:  0-7."
    ::= { ipSecEtherModeEntry 1 }

etherMode    OBJECT-TYPE
    SYNTAX INTEGER {
        off (0),
        on (1)
    }
    MAX-ACCESS read-write
    STATUS current
    DESCRIPTION
        "Mode for configured Ethernet Interface:  off or on. If a
        particular interface is on then automatically it becomes
        off for other interface. Only one interface can be turned on
        per card."
    DEFVAL {off}
    ::= { ipSecEtherModeEntry 2 }

	
-- ssh configuration related objects
	
sshMode OBJECT-TYPE
	SYNTAX INTEGER {
		off (0),
		on (1)
	}
	MAX-ACCESS read-write
	STATUS current
	DESCRIPTION
		"Flag for SSH mode."
	::= { ssh 1 }	

-- rtp transform configuration related objects

rtpTransformTable		OBJECT-TYPE
	SYNTAX SEQUENCE OF RtpTransformEntry
	MAX-ACCESS not-accessible
	STATUS current
	DESCRIPTION
		"The table is used for configuring rtp Transform data."
	::= { rtpTransform 1 }

rtpTransformEntry  OBJECT-TYPE
	SYNTAX RtpTransformEntry
        MAX-ACCESS not-accessible
        STATUS current
        DESCRIPTION
		"An entry for rtp Transform Data."
        INDEX      { rtpTransformIndex }
        ::= { rtpTransformTable 1 }

RtpTransformEntry ::= SEQUENCE {
	rtpTransformIndex	Integer32,
	rtpEncryption		INTEGER,
	rtpAuthentication	INTEGER,
	rtpTransformRowStatus	RowStatus
	}  

rtpTransformIndex	OBJECT-TYPE
	SYNTAX Integer32(0..2)
	MAX-ACCESS not-accessible
	STATUS current
	DESCRIPTION
		"Index for this table."
        ::= { rtpTransformEntry 1 }

rtpEncryption	OBJECT-TYPE
	SYNTAX INTEGER {
		null (0),
		aes (1)
	}
	MAX-ACCESS read-create
	STATUS current
	DESCRIPTION
		"RTP Transform encryption:  null or aes"
        ::= { rtpTransformEntry 2 }

rtpAuthentication	OBJECT-TYPE
	SYNTAX INTEGER {
		null (0),
		mmh2 (1),
		mmh4 (2)
	}
	MAX-ACCESS read-create
	STATUS current
	DESCRIPTION
		"RTP Transform authentication:  null, mmh2 or mmh4"
	::= { rtpTransformEntry 3 }

rtpTransformRowStatus    OBJECT-TYPE
	SYNTAX RowStatus
	MAX-ACCESS read-create
	STATUS current
	DESCRIPTION
		"The status of the row. Required to create or delete the entry in 
		this table. Only createAndGo method of row creation is supported 
		and createAndWait method is not supported."
	::= { rtpTransformEntry 4 }
	
-- rtcp transform configuration related objects

rtcpTransformTable		OBJECT-TYPE
	SYNTAX SEQUENCE OF RtcpTransformEntry
	MAX-ACCESS not-accessible
	STATUS current
	DESCRIPTION
		"The table is used for configuring rtcp Transform data."
	::= { rtcpTransform 1 }

rtcpTransformEntry  OBJECT-TYPE
	SYNTAX RtcpTransformEntry
        MAX-ACCESS not-accessible
        STATUS current
        DESCRIPTION
		"An entry for rtcp Transform Data."
        INDEX      { rtcpTransformIndex }
        ::= { rtcpTransformTable 1 }

RtcpTransformEntry ::= SEQUENCE {
	rtcpTransformIndex	Integer32,
	rtcpEncryption		INTEGER,
	rtcpAuthentication	INTEGER,
	rtcpTransformRowStatus	RowStatus
	}  

rtcpTransformIndex	OBJECT-TYPE
	SYNTAX Integer32(0..2)
	MAX-ACCESS not-accessible
	STATUS current
	DESCRIPTION
		"Index for this table."
        ::= { rtcpTransformEntry 1 }

rtcpEncryption	OBJECT-TYPE
	SYNTAX INTEGER {
		null (0),
		aes-cbc (1)
	}
	MAX-ACCESS read-create
	STATUS current
	DESCRIPTION
		"RTCP Transform encryption:  null or aes-cbc"
        ::= { rtcpTransformEntry 2 }

rtcpAuthentication	OBJECT-TYPE
	SYNTAX INTEGER {
		null (0),
		sha1 (1),
		md5 (2)
	}
	MAX-ACCESS read-create
	STATUS current
	DESCRIPTION
		"RTCP Transform authentication:  null, sha1 or md5"
	::= { rtcpTransformEntry 3 }

rtcpTransformRowStatus    OBJECT-TYPE
	SYNTAX RowStatus
	MAX-ACCESS read-create
	STATUS current
	DESCRIPTION
		"The status of the row. Required to create or delete the entry in 
		this table. Only createAndGo method of row creation is supported 
		and createAndWait method is not supported."
	::= { rtcpTransformEntry 4 }


-- port number filter related security objects

ipUnityPortNumFilterTable		OBJECT-TYPE
	SYNTAX SEQUENCE OF IpUnityPortNumFilterEntry
	MAX-ACCESS not-accessible
	STATUS current
	DESCRIPTION
		"The table is used for configuring por number filter."
	::= { ipUnityPortFilter 1 }

ipUnityPortNumFilterEntry  OBJECT-TYPE
	SYNTAX IpUnityPortNumFilterEntry
    MAX-ACCESS not-accessible
    STATUS current
    DESCRIPTION
		"An entry for port number filter Data."
    INDEX      { ipUnityPortNumFilterIfNum,ipUnityPortNumFilterIndex }
    ::= { ipUnityPortNumFilterTable 1 }

IpUnityPortNumFilterEntry ::= SEQUENCE {
	ipUnityPortNumFilterIfNum			Integer32,
	ipUnityPortNumFilterIndex    			Integer32,
	ipUnityPortNumFilterProtocol    		INTEGER,
	ipUnityPortNumFilterPortNum    		Integer32,
	ipUnityPortNumFilterRowStatus    	    RowStatus
	}  

ipUnityPortNumFilterIfNum	OBJECT-TYPE
	SYNTAX Integer32(0..7)
	MAX-ACCESS not-accessible
	STATUS current
	DESCRIPTION
		"An epif interface number."
    ::= { ipUnityPortNumFilterEntry 1 }

ipUnityPortNumFilterIndex	OBJECT-TYPE
	SYNTAX Integer32(0..15)
	MAX-ACCESS not-accessible
	STATUS current
	DESCRIPTION
		"Index for this table."
    ::= { ipUnityPortNumFilterEntry 2 }

ipUnityPortNumFilterProtocol   OBJECT-TYPE
	SYNTAX INTEGER {
		null(0),
		tcp (6),
		udp (17)
	}
	MAX-ACCESS read-create
	STATUS current
	DESCRIPTION
		"The protocol which the port is filtered."
    ::= { ipUnityPortNumFilterEntry 3 }

ipUnityPortNumFilterPortNum    OBJECT-TYPE
	SYNTAX Integer32 (0..65535)
	MAX-ACCESS read-create
	STATUS current
	DESCRIPTION
		"The port number to be filtered."
    ::= { ipUnityPortNumFilterEntry 4 }

ipUnityPortNumFilterRowStatus   OBJECT-TYPE
	SYNTAX RowStatus
	MAX-ACCESS read-create
	STATUS current
	DESCRIPTION
		"The status of the row. Required to create or delete the entry in 
		this table. Only createAndGo method of row creation is supported 
		and createAndWait method is not supported."
	::= { ipUnityPortNumFilterEntry 5 }

-- port range filter related security objects

ipUnityPortRangeFilterTable		OBJECT-TYPE
	SYNTAX SEQUENCE OF IpUnityPortRangeFilterEntry
	MAX-ACCESS not-accessible
	STATUS current
	DESCRIPTION
		"The table is used for configuring port range filter."
	::= { ipUnityPortFilter 2 }

ipUnityPortRangeFilterEntry  OBJECT-TYPE
	SYNTAX IpUnityPortRangeFilterEntry
    MAX-ACCESS not-accessible
    STATUS current
    DESCRIPTION
		"An entry for port number filter Data."
    INDEX      {ipUnityPortRangeFilterIfNum,ipUnityPortRangeFilterIndex }
    ::= { ipUnityPortRangeFilterTable 1 }

IpUnityPortRangeFilterEntry ::= SEQUENCE {
	ipUnityPortRangeFilterIfNum    		Integer32,
	ipUnityPortRangeFilterIndex		Integer32,
	ipUnityPortRangeFilterAccess    	INTEGER,
	ipUnityPortRangeFilterStartRange   Integer32,
	ipUnityPortRangeFilterEndRange     Integer32,
	ipUnityPortRangeFilterRowStatus   	RowStatus
	}  
	
ipUnityPortRangeFilterIfNum	OBJECT-TYPE
	SYNTAX Integer32(0..7)
	MAX-ACCESS not-accessible
	STATUS current
	DESCRIPTION
		"An epif interface number."
    ::= { ipUnityPortRangeFilterEntry 1 }

ipUnityPortRangeFilterIndex	OBJECT-TYPE
	SYNTAX Integer32(0..5)
	MAX-ACCESS not-accessible
	STATUS current
	DESCRIPTION
		"Index for this table."
    ::= { ipUnityPortRangeFilterEntry 2 }


ipUnityPortRangeFilterAccess   OBJECT-TYPE
	SYNTAX INTEGER {
		null(0),
		deny (1),
		allow (17)
	}
	MAX-ACCESS read-create
	STATUS current
	DESCRIPTION
		"Access The mode <allow|deny>."
    ::= { ipUnityPortRangeFilterEntry 3 }

ipUnityPortRangeFilterStartRange    OBJECT-TYPE
	SYNTAX Integer32 (1025..65535)
	MAX-ACCESS read-create
	STATUS current
	DESCRIPTION
		"ThThe range starting value."
    ::= { ipUnityPortRangeFilterEntry 4 }

ipUnityPortRangeFilterEndRange    OBJECT-TYPE
	SYNTAX Integer32 (1025..65535)
	MAX-ACCESS read-create
	STATUS current
	DESCRIPTION
		"The range end value."
    ::= { ipUnityPortRangeFilterEntry 5 }

ipUnityPortRangeFilterRowStatus  OBJECT-TYPE
	SYNTAX RowStatus
	MAX-ACCESS read-create
	STATUS current
	DESCRIPTION
		"The status of the row. Required to create or delete the entry in
                 this table. Only createAndGo method of row creation is supported
                 and createAndWait method is not supported."  

    ::= { ipUnityPortRangeFilterEntry 6 }


-- Banner group objects
	
ipUnityBannerPathFilename	OBJECT-TYPE
	SYNTAX DisplayString (SIZE (0..255))
	MAX-ACCESS read-create
	STATUS current
	DESCRIPTION
		"Path file name of the banner."
    ::= { ipUnityBannerGroup 1 }
    
ipUnityBannerHostname	OBJECT-TYPE
	SYNTAX DisplayString (SIZE (0..255))
	MAX-ACCESS read-create
	STATUS current
	DESCRIPTION
		"host name from where the banner has to be obtained."
    ::= { ipUnityBannerGroup 2 }
    
ipUnityBannerLogin	OBJECT-TYPE
	SYNTAX DisplayString (SIZE (0..255))
	MAX-ACCESS read-create
	STATUS current
	DESCRIPTION
		"User Login ID."
    ::= { ipUnityBannerGroup 3 }

ipUnityBannerPassword	OBJECT-TYPE
	SYNTAX DisplayString (SIZE (0..255))
	MAX-ACCESS read-create
	STATUS current
	DESCRIPTION
		"User password."
    ::= { ipUnityBannerGroup 4 }

ipUnityBannerCommand  OBJECT-TYPE
	SYNTAX INTEGER {
		cancel (0),
		commit (1)
	}
	MAX-ACCESS read-write
	STATUS current
	DESCRIPTION
		"Commit or Cancel the banner."
	::= { ipUnityBannerGroup 5 }

-- Software License group objects
	
ipUnitySoftwareLicenseFile	OBJECT-TYPE
	SYNTAX DisplayString
	MAX-ACCESS read-create
	STATUS current
	DESCRIPTION
		"Software license file name."
    ::= { ipUnitySoftwareLicenseGroup 1 }
    
ipUnitySoftwareLicenseHostname	OBJECT-TYPE
	SYNTAX DisplayString
	MAX-ACCESS read-create
	STATUS current
	DESCRIPTION
		"Host name from where the Software license has to be obtained."
    ::= { ipUnitySoftwareLicenseGroup 2 }
    
ipUnitySoftwareLicenseLogin	OBJECT-TYPE
	SYNTAX DisplayString
	MAX-ACCESS read-create
	STATUS current
	DESCRIPTION
		"User Login ID."
    ::= { ipUnitySoftwareLicenseGroup 3 }

ipUnitySoftwareLicensePassword	OBJECT-TYPE
	SYNTAX DisplayString
	MAX-ACCESS read-create
	STATUS current
	DESCRIPTION
		"User password."
    ::= { ipUnitySoftwareLicenseGroup 4 }


-- "other" variables needed to be sent along with traps
-- members of the group ipUnityTrapRelatedVariables

ipUnityProtocolInterfacePort	OBJECT-TYPE
        SYNTAX 	INTEGER	(0..128)
        MAX-ACCESS accessible-for-notify
        STATUS current
        DESCRIPTION
                "The value of PIF port that was used when sending the PIF port enable/disable failure trap was sent."
        ::= { ipUnityTrapRelatedVariables 1 }

ipUnityProtocolInterfaceSubPort		OBJECT-TYPE
        SYNTAX 	INTEGER	(0..128)
        MAX-ACCESS accessible-for-notify
        STATUS current
        DESCRIPTION
                "The value of PIF sub-port that was used when the PIF port enable/disable failure trap was sent."
        ::= { ipUnityTrapRelatedVariables 2 }

ipUnitySccTaskName	OBJECT-TYPE
        SYNTAX 		DisplayString (SIZE (0..127))
        MAX-ACCESS 	accessible-for-notify
        STATUS 		current
        DESCRIPTION
                "The task name associated with the last occurence of the SCC task init failure trap or the SCC task suspended trap."
        ::= { ipUnityTrapRelatedVariables 3 }

ipUnitySccFileSystemName	OBJECT-TYPE
        SYNTAX 		DisplayString (SIZE (0..127))
        MAX-ACCESS accessible-for-notify
        STATUS current
        DESCRIPTION
                "The name of the file system that was associated with the last occurence of the flash file system corrupted trap."
        ::= { ipUnityTrapRelatedVariables 4 }

ipUnitySccConfigFileName	OBJECT-TYPE
        SYNTAX 		DisplayString (SIZE (0..127))
        MAX-ACCESS 	accessible-for-notify
        STATUS 		current
        DESCRIPTION
                "The name of the configuration file that was associated with the last occurence 
		of the configuration file corrupted trap."
        ::= { ipUnityTrapRelatedVariables 5 }

ipUnitySccInstructionFileName		OBJECT-TYPE
        SYNTAX 		DisplayString (SIZE (0..127))
        MAX-ACCESS accessible-for-notify
        STATUS current
        DESCRIPTION
                "The name of the instruction file that was associated with the last occurence 
		of the instruction file not found trap on the SCC."
        ::= { ipUnityTrapRelatedVariables 6 }

ipUnitySccLogFileName		OBJECT-TYPE
        SYNTAX		DisplayString (SIZE (0..127)) 
        MAX-ACCESS accessible-for-notify
        STATUS current
        DESCRIPTION
                "The name of the SCC log file that was associated with the last occurence of the SCC log file full trap, or 
		SCC log file not found trap , or , SCC log file creation failed trap."
        ::= { ipUnityTrapRelatedVariables 7 }

ipUnityOdspAnnouncementsInstructionFileName	OBJECT-TYPE
        SYNTAX		DisplayString (SIZE (0..127)) 
        MAX-ACCESS accessible-for-notify
        STATUS current
        DESCRIPTION
                "The name of the instruction file that was associated with the last occurence of the 
		instruction file not found trap on the ODSP."
        ::= { ipUnityTrapRelatedVariables 8 }

ipUnityFailedCallAgentIpAddress		OBJECT-TYPE
        SYNTAX IpAddress
        MAX-ACCESS accessible-for-notify
        STATUS current
        DESCRIPTION
                "The IP address of the call agent with which the MGCP on the SCC failed to communicate, 
		resulting in the generation of the corresponding trap."
        ::= { ipUnityTrapRelatedVariables 9 }

ipUnityOdspTaskName	OBJECT-TYPE
        SYNTAX		DisplayString (SIZE (0..127)) 
        MAX-ACCESS accessible-for-notify
        STATUS current
        DESCRIPTION
                "The task name associated with the last occurence of the ODSP task init failure trap 
		or the ODSP task suspended trap."
        ::= { ipUnityTrapRelatedVariables 10 }

ipUnityTrapInfoString	OBJECT-TYPE
        SYNTAX          DisplayString (SIZE (0..255))
        MAX-ACCESS accessible-for-notify
        STATUS current
        DESCRIPTION
		"The optional textual description associated with any of the proprietary traps defined in the IP Unity MIB."
        ::= { ipUnityTrapRelatedVariables 11 }

ipUnityFanNumber	OBJECT-TYPE
        SYNTAX 	INTEGER (1..4)
        MAX-ACCESS accessible-for-notify
        STATUS current
        DESCRIPTION
                "The value of fan number that was used when the fan failure trap was sent."
        ::= { ipUnityTrapRelatedVariables 12 }

ipUnityPowerSupplyType	OBJECT-TYPE
        SYNTAX 	INTEGER {
                powerSupply48VoltA (1),
                powerSupply48VoltB (2),
                powerSupply5VoltA (3),
                powerSupply5VoltB (4),
                powerSupplyHot5VoltA (5),
                powerSupplyHot5VoltB (6),
                bankLowVoltage (7),
                powerSupply2point5Volt (8),
                powerSupply3Volt (9)
                }
        MAX-ACCESS accessible-for-notify
        STATUS current
        DESCRIPTION
                "The type of the power supply that failed when the power supply failure trap was sent."
        ::= { ipUnityTrapRelatedVariables 13 }

ipUnitySystemTemperature	OBJECT-TYPE
        SYNTAX  INTEGER	(0..100)
	UNITS	"degrees celsius"
        MAX-ACCESS read-only
        STATUS current
        DESCRIPTION
		" The temperature of the Media Server."
        ::= { ipUnityTrapRelatedVariables 14 }

ipUnitySystemUsagePercentage	OBJECT-TYPE
        SYNTAX  DisplayString
        MAX-ACCESS read-only
        STATUS current
        DESCRIPTION
                " The percentage of system usage of the Media Server."
        ::= { ipUnityTrapRelatedVariables 15 }

ipUnityATMUsagePercentage	OBJECT-TYPE
        SYNTAX  DisplayString
        MAX-ACCESS read-only
        STATUS current
        DESCRIPTION
                " The percentage of ATM resource usage of the Media Server."
        ::= { ipUnityTrapRelatedVariables 16 }

ipUnityMgcpUsagePercentage	OBJECT-TYPE
        SYNTAX  DisplayString
        MAX-ACCESS read-only
        STATUS current
        DESCRIPTION
                " The percentage of MGCP resource usage of the Media Server."
        ::= { ipUnityTrapRelatedVariables 17 }

ipUnityOdspLogFileName		OBJECT-TYPE
        SYNTAX		DisplayString (SIZE (0..127)) 
        MAX-ACCESS accessible-for-notify
        STATUS current
        DESCRIPTION
                "The name of the ODSP log file that was associated with the last occurence of the ODSP debug log file full 
		trap, or, ODSP debug log file not found trap."
        ::= { ipUnityTrapRelatedVariables 18 }

ipUnityTrapSeverity OBJECT-TYPE
        SYNTAX      INTEGER {
                    clear (1),
                    informational (2),
                    warning (3),
                    minor (4),
                    major (5),
                    critical (6)
        }
        MAX-ACCESS  accessible-for-notify
        STATUS      current
        DESCRIPTION
		"Gives the severity of the trap message generated by the
         	Media Server. Every trap message contains this object
         	as first object in its variable bindings."
        ::= { ipUnityTrapRelatedVariables 19 }

ipUnityDirection OBJECT-TYPE
        SYNTAX      INTEGER {
                    in (1),
                    out (2)
        }
        MAX-ACCESS  accessible-for-notify
        STATUS      current
        DESCRIPTION
        "Gives the direction in which the IP,UDP error has occured." 
        ::= { ipUnityTrapRelatedVariables 20 }

ipUnityTaskName	OBJECT-TYPE
        SYNTAX		DisplayString (SIZE (0..127)) 
        MAX-ACCESS accessible-for-notify
        STATUS current
        DESCRIPTION
                "The task name associated with the last occurence of the task init failure trap 
		or the task suspended trap."
        ::= { ipUnityTrapRelatedVariables 21 }

ipUnityLogFileName		OBJECT-TYPE
        SYNTAX		DisplayString (SIZE (0..127)) 
        MAX-ACCESS accessible-for-notify
        STATUS current
        DESCRIPTION
                "The name of the log file that was associated with the last occurence of the log file full trap, or 
		 log file not found trap , or , log file creation failed trap."
        ::= { ipUnityTrapRelatedVariables 22 }

ipUnityIpAddress        OBJECT-TYPE
        SYNTAX          DisplayString (SIZE (0..255))
        MAX-ACCESS      accessible-for-notify
        STATUS          current
        DESCRIPTION
                "The IP Address of the server."
        ::= { ipUnityTrapRelatedVariables 23 }

ipUnityLoginName        OBJECT-TYPE
        SYNTAX          DisplayString (SIZE (0..255))
        MAX-ACCESS      accessible-for-notify
        STATUS          current
        DESCRIPTION
                "The Login Name."
        ::= { ipUnityTrapRelatedVariables 24 }

ipUnitySequenceNumber	OBJECT-TYPE
        SYNTAX Integer32	
        MAX-ACCESS read-only
        STATUS current
        DESCRIPTION
                "The sequence number associated with alarms reported by CLI to help in differentiating 
		between the same type."
        ::= { ipUnityTrapRelatedVariables 25 }

ipUnityPartitionNumber OBJECT-TYPE
        SYNTAX      Integer32
        MAX-ACCESS  accessible-for-notify
        STATUS      current
        DESCRIPTION
                "The Partition number."
        ::= { ipUnityTrapRelatedVariables 26 }

ipUnityPriorityResourceUsage OBJECT-TYPE
        SYNTAX      INTEGER {
                    no (0),
                    yes (1)
        }
        MAX-ACCESS  accessible-for-notify
        STATUS      current
        DESCRIPTION
        "Gives the indication of priority resource usage. yes(1) indicates the 
	alarm is raised for priority call resource usage and no(0) indicates
	the alarm is raised for regular resource usage."
        ::= { ipUnityTrapRelatedVariables 27 }

ipUnityEPIFNumber     OBJECT-TYPE
        SYNTAX Integer32
        MAX-ACCESS accessible-for-notify
        STATUS current
        DESCRIPTION
                "EPIF number for the scc card."
        ::= { ipUnityTrapRelatedVariables 28 }


-- IP Unity notifications : classified into SCC, ODSP and "other" categories 
-- and the notifications are numbered according to the category they belong to 
-- with some scope left for adding more in the same class : so, although the V1 trap
-- numbers remain the same, the corresponding V2 notifications now have entirely
-- different numbers.


--
-- SCC "Critical" Notifications
--


ipUnitySccCpuOverload	NOTIFICATION-TYPE
	OBJECTS	{ ipUnityTrapSeverity, ipUnityCardIndex, ipUnityTrapInfoString, ipUnitySequenceNumber }
        STATUS      current
        DESCRIPTION " the CPU usage is high in the SCC ."
        ::= { ipUnityNotifications 7 }

ipUnitySccTaskSuspended	 NOTIFICATION-TYPE
        OBJECTS  { ipUnityTrapSeverity, ipUnityCardIndex, ipUnitySccTaskName, ipUnityTrapInfoString, ipUnitySequenceNumber }
        STATUS      current
        DESCRIPTION " a task in the SCC gets suspended."
        ::= { ipUnityNotifications 8 }

ipUnitySccNoMateAlarm      NOTIFICATION-TYPE
        OBJECTS  { ipUnityTrapSeverity, ipUnityCardIndex,ipUnityCardType, ipUnityTrapInfoString, ipUnitySequenceNumber }
        STATUS      current
        DESCRIPTION " the SCC does not have a mate card."
        ::= { ipUnityNotifications 14 }

ipUnitySccSwitchOverFailure	 NOTIFICATION-TYPE
        OBJECTS { ipUnityTrapSeverity, ipUnityCardIndex, ipUnityTrapInfoString, ipUnitySequenceNumber }
        STATUS      current
        DESCRIPTION " the SCC's switchover to the backup SCC has failed ."
        ::= { ipUnityNotifications 17 }

ipUnityDataSyncFailure     NOTIFICATION-TYPE
        OBJECTS { ipUnityTrapSeverity, ipUnityCardIndex, ipUnityTrapInfoString, ipUnitySequenceNumber }
        STATUS      current
        DESCRIPTION " the data synchronization fails between the SCCs."
        ::= { ipUnityNotifications 19 }

ipUnitySccTaskResumeFailed	NOTIFICATION-TYPE
        OBJECTS  { ipUnityTrapSeverity, ipUnityCardIndex , ipUnitySccTaskName, ipUnityTrapInfoString, ipUnitySequenceNumber }
        STATUS      current
        DESCRIPTION " a task resumption fails in the SCC."
        ::= { ipUnityNotifications 20 }

ipUnityNoInterface NOTIFICATION-TYPE
        OBJECTS  { ipUnityTrapSeverity, ipUnityCardIndex, ipUnityTrapInfoString, ipUnitySequenceNumber, ipUnityEPIFNumber }
        STATUS      current
        DESCRIPTION "The given ethernet interface ipUnityEPIFNumber has a change in link status. Severity clear
                     means the link is UP."
        ::= { ipUnityNotifications 21 }

ipUnitySccCompactFlashCheckDisk  NOTIFICATION-TYPE
        OBJECTS  { ipUnityTrapSeverity, ipUnityCardIndex, ipUnitySccFileSystemName, ipUnityTrapInfoString, ipUnitySequenceNumber }
        STATUS      current
        DESCRIPTION " Check disk error in the the Compact flash."
        ::= { ipUnityNotifications 22 }

ipUnitySccMgcpError     NOTIFICATION-TYPE
        OBJECTS { ipUnityTrapSeverity, ipUnityCardIndex, ipUnityTrapInfoString, ipUnitySequenceNumber }
        STATUS      current
        DESCRIPTION " SCC MGCP error."
        ::= { ipUnityNotifications 23 }

ipUnityAtmCommFailure     NOTIFICATION-TYPE
        OBJECTS { ipUnityTrapSeverity, ipUnityCardIndex, ipUnityTrapInfoString, ipUnitySequenceNumber }
        STATUS      current
        DESCRIPTION " Atm Communication Failure."
        ::= { ipUnityNotifications 24 }

ipUnitySccAtmSoftwareInitFailure     NOTIFICATION-TYPE
        OBJECTS { ipUnityTrapSeverity, ipUnityCardIndex, ipUnityTrapInfoString, ipUnitySequenceNumber }
        STATUS      current
        DESCRIPTION " Atm Software Init Failure."
        ::= { ipUnityNotifications 25 }

ipUnitySccAtmSarInitFailure     NOTIFICATION-TYPE
        OBJECTS { ipUnityTrapSeverity, ipUnityCardIndex, ipUnityTrapInfoString, ipUnitySequenceNumber }
        STATUS      current
        DESCRIPTION " Atm Software SAR Init Failure."
        ::= { ipUnityNotifications 26 }

ipUnitySccFlash1CheckDisk   NOTIFICATION-TYPE
        OBJECTS  { ipUnityTrapSeverity, ipUnityCardIndex , ipUnityTrapInfoString, ipUnitySequenceNumber }
        STATUS      current
        DESCRIPTION "Flash1 Checkdisk error."
        ::= { ipUnityNotifications 27 }
        
ipUnitySccFlash2CheckDisk   NOTIFICATION-TYPE
        OBJECTS  { ipUnityTrapSeverity, ipUnityCardIndex , ipUnityTrapInfoString, ipUnitySequenceNumber }
        STATUS      current
        DESCRIPTION "Flash2 Checkdisk error."
        ::= { ipUnityNotifications 28 }
        
ipUnitySccFlash1AuditFailure   NOTIFICATION-TYPE
        OBJECTS  { ipUnityTrapSeverity, ipUnityCardIndex , ipUnityTrapInfoString, ipUnitySequenceNumber }
        STATUS      current
        DESCRIPTION "Flash1 Audit Failure."
        ::= { ipUnityNotifications 29 }

ipUnitySccAlternateImageBoot   NOTIFICATION-TYPE
        OBJECTS  { ipUnityTrapSeverity, ipUnityCardIndex, ipUnityTrapInfoString, ipUnitySequenceNumber }
        STATUS      current
        DESCRIPTION "SCC Alternate Image boot."
        ::= { ipUnityNotifications 30 }

--
--
-- SCC "Major" Notifications (31-55)
--


ipUnitySccFileSystemFailure 	NOTIFICATION-TYPE
        OBJECTS  { ipUnityTrapSeverity, ipUnityCardIndex, ipUnitySccFileSystemName, ipUnityTrapInfoString, ipUnitySequenceNumber }
        STATUS      current
        DESCRIPTION " some failure or error is detected in the file system in the SCC."
        ::= { ipUnityNotifications 31 }

ipUnitySccResourceShortage	NOTIFICATION-TYPE
        OBJECTS { ipUnityTrapSeverity, ipUnityCardIndex, ipUnityTrapInfoString, ipUnityPartitionNumber, ipUnitySequenceNumber }
        STATUS      current
        DESCRIPTION " there is a resource shortage in the Media Server."
        ::= { ipUnityNotifications 37 }

ipUnitySccFileSystemHighUsage  NOTIFICATION-TYPE
        OBJECTS  { ipUnityTrapSeverity, ipUnityCardIndex, ipUnitySccFileSystemName, ipUnityTrapInfoString, ipUnitySequenceNumber }
        STATUS      current
        DESCRIPTION " the file system usage exceeds the threshold in the SCC."
        ::= { ipUnityNotifications 40 }

ipUnitySccImageSyncFailure	NOTIFICATION-TYPE
        OBJECTS  { ipUnityTrapSeverity, ipUnityCardIndex, ipUnityTrapInfoString, ipUnitySequenceNumber }
        STATUS      current
        DESCRIPTION " the synchronization of the image fails between the active SCC and 
			the standby SCC."
        ::= { ipUnityNotifications 42 }

ipUnitySccUpgradeFailure	NOTIFICATION-TYPE
        OBJECTS  { ipUnityTrapSeverity, ipUnityCardIndex, ipUnityTrapInfoString, ipUnitySequenceNumber }
        STATUS      current
        DESCRIPTION " the upgrade of the SCC image fails."
        ::= { ipUnityNotifications 43 }

ipUnitySccVersionMismatch	NOTIFICATION-TYPE
        OBJECTS  { ipUnityTrapSeverity, ipUnityCardIndex, ipUnityCardType, ipUnityTrapInfoString, ipUnitySequenceNumber }
        STATUS      current
        DESCRIPTION " the SCC version mismatch occurs."
        ::= { ipUnityNotifications 45 }

ipUnitySccMemoryLow	NOTIFICATION-TYPE
	OBJECTS	{ ipUnityTrapSeverity, ipUnityCardIndex, ipUnityTrapInfoString, ipUnitySequenceNumber }
        STATUS      current
        DESCRIPTION " the free memory is very low in the SCC."
        ::= { ipUnityNotifications 46 }

ipUnitySccInterhostCommunicationFailure	NOTIFICATION-TYPE
	OBJECTS	{ ipUnityTrapSeverity, ipUnityCardIndex, ipUnityTrapInfoString, ipUnitySequenceNumber }
        STATUS      current
        DESCRIPTION " the SCC fails to communicate with another card in the Media Server."
        ::= { ipUnityNotifications 47 }

ipUnitySccFlashFileCorrupt 	NOTIFICATION-TYPE
        OBJECTS  { ipUnityTrapSeverity, ipUnityCardIndex, ipUnitySccFileSystemName, ipUnityTrapInfoString, ipUnitySequenceNumber }
        STATUS      current
        DESCRIPTION " the flash in the SCC is corrupted."
        ::= { ipUnityNotifications 53 }

ipUnityAnnSyncFailure NOTIFICATION-TYPE
        OBJECTS  { ipUnityTrapSeverity, ipUnityCardIndex, ipUnityTrapInfoString, ipUnitySequenceNumber }
        STATUS      current
        DESCRIPTION "" 
        ::= { ipUnityNotifications 56 }

ipUnityConfigSyncFailure NOTIFICATION-TYPE
        OBJECTS  { ipUnityTrapSeverity, ipUnityCardIndex, ipUnityTrapInfoString, ipUnitySequenceNumber }
        STATUS      current
        DESCRIPTION "" 
        ::= { ipUnityNotifications 57 }

ipUnitySccCompactFlashAuditFailure NOTIFICATION-TYPE
    OBJECTS { ipUnityTrapSeverity, ipUnityCardIndex, ipUnityTrapInfoString, ipUnitySequenceNumber }
        STATUS      current
        DESCRIPTION " the SCC compact flash audit failure."
        ::= { ipUnityNotifications 58 }

ipUnitySccCompactFlashInitFailure NOTIFICATION-TYPE
    OBJECTS { ipUnityTrapSeverity, ipUnityCardIndex, ipUnityTrapInfoString, ipUnitySequenceNumber }
        STATUS      current
        DESCRIPTION " the SCC compact flash Init failure."
        ::= { ipUnityNotifications 59 }

ipUnitySccFlash1InitFailure NOTIFICATION-TYPE
    OBJECTS { ipUnityTrapSeverity, ipUnityCardIndex, ipUnityTrapInfoString, ipUnitySequenceNumber }
        STATUS      current
        DESCRIPTION " the flash1 Init failure."
        ::= { ipUnityNotifications 60 }

ipUnitySccFlash2InitFailure NOTIFICATION-TYPE
    OBJECTS { ipUnityTrapSeverity, ipUnityCardIndex, ipUnityTrapInfoString, ipUnitySequenceNumber }
        STATUS      current
        DESCRIPTION " the flash2 Init failure."
        ::= { ipUnityNotifications 61 }

ipUnitySccI2CInitFailure NOTIFICATION-TYPE
    OBJECTS { ipUnityTrapSeverity, ipUnityCardIndex, ipUnityTrapInfoString, ipUnitySequenceNumber }
        STATUS      current
        DESCRIPTION " the I2C Init failure."
        ::= { ipUnityNotifications 62 }

--
-- SCC "Minor" Notifications (62-80)
--
ipUnitySystemHighUsage	NOTIFICATION-TYPE
        OBJECTS  { ipUnityTrapSeverity, ipUnitySystemUsagePercentage, ipUnityTrapInfoString, ipUnitySequenceNumber }
        STATUS      current
        DESCRIPTION " the system usage exceeds the threshold."
        ::= { ipUnityNotifications 63 }

ipUnitySccSoftwareError	NOTIFICATION-TYPE
        OBJECTS { ipUnityTrapSeverity, ipUnityCardIndex, ipUnityTrapInfoString, ipUnitySequenceNumber }
        STATUS      current
        DESCRIPTION " a software error occurs on the SCC."
        ::= { ipUnityNotifications 70 }

ipUnitySccNTPSync        NOTIFICATION-TYPE
        OBJECTS { ipUnityTrapSeverity, ipUnityCardIndex, ipUnityTrapInfoString, ipUnitySequenceNumber }
        STATUS      current
        DESCRIPTION " an NTP sync error occurs on the SCC."
        ::= { ipUnityNotifications 71 }

ipUnityPartitionHighUsage	NOTIFICATION-TYPE
        OBJECTS { ipUnityTrapSeverity, ipUnityTrapInfoString, ipUnityPartitionNumber, ipUnitySequenceNumber }
        STATUS      current
        DESCRIPTION " the usage of a partition in the Media Server 
			exceeds the threshold for usage."
        ::= { ipUnityNotifications 72 }
	
ipUnityIvrHighUsage	NOTIFICATION-TYPE
        OBJECTS { ipUnityTrapSeverity, ipUnityTrapInfoString, ipUnityPartitionNumber, ipUnitySequenceNumber, ipUnityPriorityResourceUsage }
        STATUS      current
        DESCRIPTION " the usage of IVR resources in the Media
			Server exceeds the threshold for IVR usage."
        ::= { ipUnityNotifications 73 }

ipUnityReservedConferenceHighUsage	NOTIFICATION-TYPE
        OBJECTS { ipUnityTrapSeverity, ipUnityTrapInfoString, ipUnityPartitionNumber, ipUnitySequenceNumber, ipUnityPriorityResourceUsage }
        STATUS      current
        DESCRIPTION " the usage of Reserved Conference resources
			in the Media Server exceeds the threshold for Reserved
			Conference usage."
        ::= { ipUnityNotifications 74 }

ipUnityAdHocConferenceHighUsage		NOTIFICATION-TYPE
        OBJECTS { ipUnityTrapSeverity, ipUnityTrapInfoString, ipUnityPartitionNumber, ipUnitySequenceNumber, ipUnityPriorityResourceUsage }
        STATUS      current
        DESCRIPTION " the usage of AdHoc Conference resources
                        in the Media Server exceeds the threshold for AdHoc
			Conference usage."
        ::= { ipUnityNotifications 75 }

ipUnityAsrHighUsage 	NOTIFICATION-TYPE
        OBJECTS  { ipUnityTrapSeverity, ipUnityTrapInfoString, ipUnityPartitionNumber, ipUnitySequenceNumber }
        STATUS      current
        DESCRIPTION " the ASR usage, as detected on the SCC, exceeds the desired threshold."
        ::= { ipUnityNotifications 76 }

ipUnityVxmlHighUsage	NOTIFICATION-TYPE
        OBJECTS  { ipUnityTrapSeverity, ipUnityTrapInfoString, ipUnityPartitionNumber, ipUnitySequenceNumber }
        STATUS      current
        DESCRIPTION " the VXML usage, as detected on the SCC, exceeds the desired threshold."
        ::= { ipUnityNotifications 77 }

ipUnityHttpHighUsage	NOTIFICATION-TYPE
        OBJECTS  { ipUnityTrapSeverity, ipUnityTrapInfoString, ipUnityPartitionNumber, ipUnitySequenceNumber }
        STATUS      current
        DESCRIPTION " the HTTP usage, as detected on the SCC, exceeds the desired threshold."
        ::= { ipUnityNotifications 78 }

ipUnityTimeOfDayError	NOTIFICATION-TYPE
        OBJECTS { ipUnityTrapSeverity, ipUnityTrapInfoString, ipUnitySequenceNumber }
        STATUS      current
        DESCRIPTION " the Time Of Day is in error."
        ::= { ipUnityNotifications 79 }

ipUnityConfigError	NOTIFICATION-TYPE
        OBJECTS { ipUnityTrapSeverity, ipUnityTrapInfoString, ipUnitySequenceNumber }
        STATUS      current
        DESCRIPTION "This is the initial threshold warning that the memory is getting consumed 
                     at a large rate."
        ::= { ipUnityNotifications 81 }

--
-- SCC "Info" Notifications
--


ipUnitySccDebugLogFull	NOTIFICATION-TYPE
        OBJECTS  { ipUnityTrapSeverity, ipUnityCardIndex, ipUnitySccLogFileName, ipUnityTrapInfoString, ipUnitySequenceNumber }
        STATUS      current
        DESCRIPTION " the logging media is full in the SCC."
        ::= { ipUnityNotifications 82 }

ipUnityLongDurationCall		NOTIFICATION-TYPE
        OBJECTS  { ipUnityTrapSeverity, ipUnityCardIndex, ipUnityTrapInfoString, ipUnitySequenceNumber }
        STATUS      current
        DESCRIPTION " a long duration call is detected in the SCC."
        ::= { ipUnityNotifications 88 }

ipUnityHungCall		NOTIFICATION-TYPE
        OBJECTS  { ipUnityTrapSeverity, ipUnityCardIndex, ipUnityTrapInfoString, ipUnitySequenceNumber }
        STATUS      current
        DESCRIPTION " a hung call is detected in the SCC."
        ::= { ipUnityNotifications 89 }

ipUnityChannelLockout	NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " a channel lockout is detected in the SCC."
        ::= { ipUnityNotifications 90 }

ipUnitySimplexMode      NOTIFICATION-TYPE
        OBJECTS  { ipUnityTrapSeverity, ipUnityCardIndex,ipUnityCardType, ipUnityTrapInfoString, ipUnitySequenceNumber }
        STATUS      current
        DESCRIPTION " the Media Server is observed to be running in Simplex mode."
        ::= { ipUnityNotifications 95 }

ipUnitySccSwitchOver NOTIFICATION-TYPE
	  OBJECTS	{ ipUnityTrapSeverity, ipUnityCardIndex, ipUnityTrapInfoString, ipUnitySequenceNumber }
        STATUS      current
        DESCRIPTION " the SCC switches over to the backup, or redundancy, SCC."
        ::= { ipUnityNotifications 96 }

ipUnityNoRoute NOTIFICATION-TYPE
        OBJECTS { ipUnityTrapSeverity, ifIndex, ipUnityTrapInfoString, ipUnitySequenceNumber }
        STATUS      current
        DESCRIPTION ""
        ::= { ipUnityNotifications 97 }

ipUnityDuplicateAnnouncement NOTIFICATION-TYPE
        OBJECTS { ipUnityTrapSeverity, ipUnityCardIndex, ipUnityBankIndex, ipUnityTrapInfoString, ipUnitySequenceNumber }
        STATUS      current
        DESCRIPTION ""
        ::= { ipUnityNotifications 98 }

ipUnityNoLicenseInNVRAM     NOTIFICATION-TYPE
        OBJECTS  { ipUnityTrapSeverity, ipUnityCardIndex, ipUnityTrapInfoString, ipUnitySequenceNumber }
        STATUS      current
        DESCRIPTION " No License in NVRAM error."
        ::= { ipUnityNotifications 99 }

ipUnityChassisIDMismatch NOTIFICATION-TYPE
        OBJECTS  { ipUnityTrapSeverity, ipUnityCardIndex, ipUnityTrapInfoString, ipUnitySequenceNumber }
        STATUS      current
        DESCRIPTION " Chassis ID mismatch error."
        ::= { ipUnityNotifications 100 }

--
-- ODSP "Critical" Notifications
--



ipUnityOdspTaskSuspended        NOTIFICATION-TYPE
        OBJECTS  { ipUnityTrapSeverity, ipUnityCardIndex , ipUnityBankIndex, ipUnityOdspTaskName, ipUnityTrapInfoString, ipUnitySequenceNumber }
        STATUS      current
        DESCRIPTION " a task gets suspended in a bank."
        ::= { ipUnityNotifications 102 }

ipUnityOdspTaskResumeFailed	NOTIFICATION-TYPE
        OBJECTS  { ipUnityTrapSeverity, ipUnityCardIndex , ipUnityBankIndex, ipUnityOdspTaskName, ipUnityTrapInfoString, ipUnitySequenceNumber }
        STATUS      current
        DESCRIPTION " a task resumption fails in a bank."
        ::= { ipUnityNotifications 103 }

ipUnityAnnFileFailure NOTIFICATION-TYPE
        OBJECTS  { ipUnityTrapSeverity, ipUnityCardIndex , ipUnityBankIndex, ipUnityTrapInfoString, ipUnitySequenceNumber }
        STATUS      current
        DESCRIPTION " ANN FILE failure in the ODSP."
        ::= { ipUnityNotifications 104 }

ipUnityDisableDSPBank NOTIFICATION-TYPE
        OBJECTS  { ipUnityTrapSeverity, ipUnityCardIndex,ipUnityBankIndex, ipUnityTrapInfoString, ipUnitySequenceNumber }
        STATUS      current
        DESCRIPTION " a DSP bank is disabled in a card."
        ::= { ipUnityNotifications 105 }

ipUnityBankReset NOTIFICATION-TYPE
        OBJECTS  { ipUnityTrapSeverity, ipUnityCardIndex,ipUnityBankIndex, ipUnityTrapInfoString, ipUnitySequenceNumber }
        STATUS      current
        DESCRIPTION "a bank is reset in a card."
        ::= { ipUnityNotifications 107 }

ipUnityOdspAtmSarInitFailure NOTIFICATION-TYPE
        OBJECTS  { ipUnityTrapSeverity, ipUnityCardIndex,ipUnityBankIndex, ipUnityTrapInfoString, ipUnitySequenceNumber }
        STATUS      current
        DESCRIPTION "Atm Sar Init Failure."
        ::= { ipUnityNotifications 108 }

ipUnityOdspFlash1CheckDisk   NOTIFICATION-TYPE
        OBJECTS  { ipUnityTrapSeverity, ipUnityCardIndex , ipUnityBankIndex, ipUnityTrapInfoString, ipUnitySequenceNumber }
        STATUS      current
        DESCRIPTION "Flash1 Checkdisk error."
        ::= { ipUnityNotifications 109 }

ipUnityOdspFlash2CheckDisk   NOTIFICATION-TYPE
        OBJECTS  { ipUnityTrapSeverity, ipUnityCardIndex , ipUnityBankIndex, ipUnityTrapInfoString, ipUnitySequenceNumber }
        STATUS      current
        DESCRIPTION "Flash2 Checkdisk error."
        ::= { ipUnityNotifications 110 }

--
-- ODSP "Major" Notifications
--

ipUnityOdspAnnouncementDownloadFailure	NOTIFICATION-TYPE
        OBJECTS  { ipUnityTrapSeverity, ipUnityCardIndex , ipUnityBankIndex, ipUnityTrapInfoString, ipUnitySequenceNumber }
        STATUS      current
        DESCRIPTION " an announcement download failure occurs at a bank."
        ::= { ipUnityNotifications 121 }

ipUnityOdspDspCommunicationFailure	NOTIFICATION-TYPE
        OBJECTS  { ipUnityTrapSeverity, ipUnityCardIndex , ipUnityBankIndex, ipUnityModuleIndex, ipUnityTrapInfoString, ipUnitySequenceNumber }
        STATUS      current
        DESCRIPTION " a DSP cannot communicate with its Odsp bank any more."
        ::= { ipUnityNotifications 123 }

ipUnityOdspCpuOverload 	NOTIFICATION-TYPE
        OBJECTS  { ipUnityTrapSeverity, ipUnityCardIndex , ipUnityBankIndex, ipUnityTrapInfoString, ipUnitySequenceNumber }
        STATUS      current
        DESCRIPTION " a bank's CPU usage exceeds the threshold value."
        ::= { ipUnityNotifications 126 }

ipUnityOdspMemoryLow	NOTIFICATION-TYPE
        OBJECTS  { ipUnityTrapSeverity, ipUnityCardIndex , ipUnityBankIndex, ipUnityTrapInfoString, ipUnitySequenceNumber }
        STATUS      current
        DESCRIPTION " the free memory is very low for a bank."
        ::= { ipUnityNotifications 127 }

ipUnityOdspSccCommunicationFailure	NOTIFICATION-TYPE
        OBJECTS  { ipUnityTrapSeverity, ipUnityCardIndex , ipUnityBankIndex, ipUnityTrapInfoString, ipUnitySequenceNumber }
        STATUS      current
        DESCRIPTION " the bank can no longer communicate with the SCC."
        ::= { ipUnityNotifications 129 }

ipUnityOdspSoftwareException	NOTIFICATION-TYPE
        OBJECTS { ipUnityTrapSeverity, ipUnityCardIndex, ipUnityBankIndex, ipUnityTrapInfoString, ipUnitySequenceNumber }
        STATUS      current
        DESCRIPTION " a software exception occurs in the bank."
        ::= { ipUnityNotifications 133 }

ipUnityOdspSoftwareError	NOTIFICATION-TYPE
        OBJECTS { ipUnityTrapSeverity, ipUnityCardIndex, ipUnityBankIndex, ipUnityTrapInfoString, ipUnitySequenceNumber }
        STATUS      current
        DESCRIPTION " a software error occurs in the bank."
        ::= { ipUnityNotifications 134 }

ipUnityOdspFileSystemFailure 	NOTIFICATION-TYPE
        OBJECTS  { ipUnityTrapSeverity, ipUnityCardIndex, ipUnityBankIndex, ipUnityTrapInfoString, ipUnitySequenceNumber }
        STATUS      current
        DESCRIPTION " a failure is detected in the file system in the ODSP."
        ::= { ipUnityNotifications 137 }

ipUnityOdspFileSystemHighUsage  NOTIFICATION-TYPE
        OBJECTS  { ipUnityTrapSeverity, ipUnityCardIndex, ipUnityBankIndex, ipUnityTrapInfoString, ipUnitySequenceNumber }
        STATUS      current
        DESCRIPTION " the file system usage exceeds the threshold in the ODSP."
        ::= { ipUnityNotifications 138 }

ipUnityOdspImageSyncFailure      NOTIFICATION-TYPE
        OBJECTS  { ipUnityTrapSeverity, ipUnityCardIndex, ipUnityBankIndex, ipUnityTrapInfoString, ipUnitySequenceNumber }
        STATUS      current
        DESCRIPTION " the synchronization of the image fails between the active ODSP 
			and the standby ODSP."
        ::= { ipUnityNotifications 141 }

ipUnityOdspUpgradeFailure        NOTIFICATION-TYPE
        OBJECTS  { ipUnityTrapSeverity, ipUnityCardIndex, ipUnityBankIndex, ipUnityTrapInfoString, ipUnitySequenceNumber }
        STATUS      current
        DESCRIPTION " the upgrade of the ODSP image fails."
        ::= { ipUnityNotifications 142 }

ipUnityOdspVersionMismatch       NOTIFICATION-TYPE
        OBJECTS  { ipUnityTrapSeverity, ipUnityCardIndex, ipUnityBankIndex, ipUnityTrapInfoString, ipUnitySequenceNumber }
        STATUS      current
        DESCRIPTION " the ODSP version mismatch occurs."
        ::= { ipUnityNotifications 144 }

ipUnityDisableDSPModule NOTIFICATION-TYPE
        OBJECTS  { ipUnityTrapSeverity, ipUnityCardIndex, ipUnityBankIndex,ipUnityModuleIndex, ipUnityTrapInfoString, ipUnitySequenceNumber }
        STATUS      current
        DESCRIPTION " a DSP module is disabled in a bank."
        ::= { ipUnityNotifications 145 }

ipUnityOdspDspCpuOverload	NOTIFICATION-TYPE
        OBJECTS  { ipUnityTrapSeverity, ipUnityCardIndex , ipUnityBankIndex, ipUnityModuleIndex, ipUnityTrapInfoString, ipUnitySequenceNumber }
        STATUS      current
        DESCRIPTION " a DSP's CPU is overloaded with traffic."
        ::= { ipUnityNotifications 147 }

ipUnityOdspDspSpareUnavailable	NOTIFICATION-TYPE
        OBJECTS  { ipUnityTrapSeverity, ipUnityCardIndex , ipUnityBankIndex, ipUnityModuleIndex, ipUnityTrapInfoString, ipUnitySequenceNumber }
        STATUS      current
        DESCRIPTION " a ODSP module losts its DSP resources due to outage."
        ::= { ipUnityNotifications 148 }

ipUnityOdspAtmCommFail	NOTIFICATION-TYPE
        OBJECTS  { ipUnityTrapSeverity, ipUnityCardIndex , ipUnityBankIndex, ipUnityTrapInfoString, ipUnitySequenceNumber }
        STATUS      current
        DESCRIPTION " a ODSP ATN heartbeat detects that the PIF module is not
                     receiving packets."
        ::= { ipUnityNotifications 149 }

ipUnityOdspFlash1InitFailure  NOTIFICATION-TYPE
        OBJECTS  { ipUnityTrapSeverity, ipUnityCardIndex , ipUnityBankIndex, ipUnityTrapInfoString, ipUnitySequenceNumber }
        STATUS      current
        DESCRIPTION " a ODSP flash1 Init Failure."
        ::= { ipUnityNotifications 150 }

ipUnityOdspFlash2InitFailure  NOTIFICATION-TYPE
        OBJECTS  { ipUnityTrapSeverity, ipUnityCardIndex , ipUnityBankIndex, ipUnityTrapInfoString, ipUnitySequenceNumber }
        STATUS      current
        DESCRIPTION " a ODSP flash1 Init Failure."
        ::= { ipUnityNotifications 151 }

--
-- ODSP "Minor" Notifications
--
-- Changed to Module Software Error

ipUnityModuleSoftwareException	NOTIFICATION-TYPE
        OBJECTS { ipUnityTrapSeverity, ipUnityCardIndex, ipUnityBankIndex, ipUnityModuleIndex, ipUnityTrapInfoString, ipUnitySequenceNumber }
        STATUS      current
        DESCRIPTION " a software exception occurs in a bank."
        ::= { ipUnityNotifications 164 }

ipUnityModuleSoftwareError	NOTIFICATION-TYPE
        OBJECTS { ipUnityTrapSeverity, ipUnityCardIndex, ipUnityBankIndex, ipUnityModuleIndex, ipUnityTrapInfoString, ipUnitySequenceNumber }
        STATUS      current
        DESCRIPTION " a software error occurs in a bank."
        ::= { ipUnityNotifications 165 }


ipUnityOdspNTPSync        NOTIFICATION-TYPE
        OBJECTS { ipUnityTrapSeverity, ipUnityCardIndex, ipUnityBankIndex, ipUnityTrapInfoString, ipUnitySequenceNumber }
        STATUS      current
        DESCRIPTION " an NTP sync error occurs in an ODSP."
        ::= { ipUnityNotifications 166 }

ipUnityDspSpuriousReset		NOTIFICATION-TYPE
        OBJECTS  { ipUnityTrapSeverity, ipUnityCardIndex , ipUnityBankIndex, ipUnityModuleIndex, ipUnityTrapInfoString, ipUnitySequenceNumber }
        STATUS      current
        DESCRIPTION " a spurious reset occurs on a DSP in a bank."
        ::= { ipUnityNotifications 167 }

ipUnityOdspDspChannelNoRTP		NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " a channel belonging to a DSP in a bank cannot send or receive RTP data."
        ::= { ipUnityNotifications 172 }

ipUnityOdspDspChannelPacketLossLow		NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " the packet loss is observed to be low on a DSP channel."
        ::= { ipUnityNotifications 173 }

ipUnityOdspDspChannelPacketLossHigh	NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " the packet loss is observed to be high on a DSP channel."
        ::= { ipUnityNotifications 174 }

ipUnityOdspDspChannelPayloadMismatch	 NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " a payload mismatch is detected in a channel belonging to a DSP."
        ::= { ipUnityNotifications 175 }

ipUnityOdspDspInitFailure	NOTIFICATION-TYPE
        OBJECTS  { ipUnityTrapSeverity, ipUnityCardIndex , ipUnityBankIndex, ipUnityModuleIndex, ipUnityTrapInfoString, ipUnitySequenceNumber }
        STATUS      current
        DESCRIPTION " a DSP fails to initialize."
        ::= { ipUnityNotifications 176 }

ipUnityDspCPMTransmitFailure	NOTIFICATION-TYPE
        OBJECTS  { ipUnityTrapSeverity, ipUnityCardIndex , ipUnityBankIndex, ipUnityModuleIndex, ipUnityTrapInfoString, ipUnitySequenceNumber }
        STATUS      current
        DESCRIPTION " one of the DSPs in a bank fails to transmit to the CPM for that bank."
        ::= { ipUnityNotifications 177 }

ipUnityModuleHighUsage	NOTIFICATION-TYPE
        OBJECTS  { ipUnityTrapSeverity, ipUnityCardIndex , ipUnityBankIndex, ipUnityModuleIndex, ipUnityTrapInfoString, ipUnitySequenceNumber }
        STATUS      current
        DESCRIPTION " a module in a bank is used very heavily."
        ::= { ipUnityNotifications 178 }

ipUnityOdspBankHighUsage	NOTIFICATION-TYPE
        OBJECTS  { ipUnityTrapSeverity, ipUnityCardIndex , ipUnityBankIndex, ipUnityTrapInfoString, ipUnitySequenceNumber }
        STATUS      current
        DESCRIPTION " a bank in an MPC is used very heavily."
        ::= { ipUnityNotifications 179 }

ipUnityOdspModuleFwdQFull	NOTIFICATION-TYPE
        OBJECTS  { ipUnityTrapSeverity, ipUnityCardIndex , ipUnityBankIndex, ipUnityModuleIndex, ipUnityTrapInfoString, ipUnitySequenceNumber }
        STATUS      current
        DESCRIPTION " a module in a DSP bank detects that it can not 
                     transmit packet towards the network."
        ::= { ipUnityNotifications 181 }

ipUnityBankFlashCorrupt         NOTIFICATION-TYPE
        OBJECTS  { ipUnityTrapSeverity, ipUnityCardIndex, ipUnityBankIndex, ipUnityTrapInfoString, ipUnitySequenceNumber }
        STATUS  current
        DESCRIPTION "Bank Flash Corrupt is raised whenever the system audit detects that an Flash is Corrupt"
        ::= { ipUnityNotifications 183 }


--
-- ODSP "Info" Notifications
--



ipUnityOdspDebugLogFull     NOTIFICATION-TYPE
        OBJECTS  { ipUnityTrapSeverity, ipUnityCardIndex, ipUnityBankIndex, ipUnityOdspLogFileName, ipUnityTrapInfoString, ipUnitySequenceNumber }
        STATUS      current
        DESCRIPTION " the debug log is full in the ODSP."
        ::= { ipUnityNotifications 191 }

ipUnityOdspNASMountFailure      NOTIFICATION-TYPE
        OBJECTS  { ipUnityTrapSeverity, ipUnityCardIndex , ipUnityBankIndex, ipUnityModuleIndex, ipUnityTrapInfoString, ipUnitySequenceNumber }
        STATUS      current
        DESCRIPTION " the NAS mount process fails for a DSP."
        ::= { ipUnityNotifications 193 }

--
-- Other "Critical" Notifications
--


ipUnityFanFailure NOTIFICATION-TYPE
	OBJECTS	{ ipUnityTrapSeverity, ipUnityFanNumber, ipUnityTrapInfoString, ipUnitySequenceNumber }
        STATUS      current
        DESCRIPTION " the failure of a fan is detected in the media server."
        ::= { ipUnityNotifications 202 }

ipUnitySystemTemperatureHigh NOTIFICATION-TYPE
	OBJECTS	{ ipUnityTrapSeverity, ipUnitySystemTemperature, ipUnityTrapInfoString, ipUnitySequenceNumber }
        STATUS      current
        DESCRIPTION " the system temperature has exceeded the desired range."
        ::= { ipUnityNotifications 203 }

ipUnityI2CPowerSupplyAlarm      NOTIFICATION-TYPE
        OBJECTS  { ipUnityTrapSeverity, ipUnityPowerSupplyType, ipUnityTrapInfoString, ipUnitySequenceNumber }
        STATUS      current
        DESCRIPTION " an I2C power supply failure occurs in the Media Server."
        ::= { ipUnityNotifications 204 }


--
-- Other "Major" Notifications
--

ipUnityResetCard NOTIFICATION-TYPE
        OBJECTS  { ipUnityTrapSeverity, ipUnityCardIndex,ipUnityCardType, ipUnityTrapInfoString, ipUnitySequenceNumber }
        STATUS      current
        DESCRIPTION " a card is reset , i.e. a power cycle is sent through it, in the Media Server."
        ::= { ipUnityNotifications 241 }

ipUnityDisableCard NOTIFICATION-TYPE
        OBJECTS  { ipUnityTrapSeverity, ipUnityCardIndex,ipUnityCardType, ipUnityTrapInfoString, ipUnitySequenceNumber }
        STATUS      current
        DESCRIPTION " a card is disabled in the Media Server."
        ::= { ipUnityNotifications 244 }

ipUnityRemoveCard NOTIFICATION-TYPE
        OBJECTS  { ipUnityTrapSeverity, ipUnityCardIndex,ipUnityCardType, ipUnityTrapInfoString, ipUnitySequenceNumber }
        STATUS      current
        DESCRIPTION " a card is removed from the Media Server ."
        ::= { ipUnityNotifications 246 }

--
-- "Other Info" Notifications
--


ipUnityTtsHighUsage	NOTIFICATION-TYPE
        OBJECTS  { ipUnityTrapSeverity, ipUnityTrapInfoString, ipUnityPartitionNumber, ipUnitySequenceNumber }
        STATUS      current
        DESCRIPTION "TTS usage, as detected on the SCC, exceeds the desired threshold."
        ::= { ipUnityNotifications 290 }

ipUnityFaxHighUsage	NOTIFICATION-TYPE
        OBJECTS  { ipUnityTrapSeverity, ipUnityTrapInfoString, ipUnityPartitionNumber, ipUnitySequenceNumber, ipUnityPriorityResourceUsage }
        STATUS      current
        DESCRIPTION "FAX usage, as detected on the SCC, exceeds the desired threshold."
        ::= { ipUnityNotifications 291 }

ipUnityIcmHighUsage	NOTIFICATION-TYPE
        OBJECTS  { ipUnityTrapSeverity, ipUnityTrapInfoString, ipUnityPartitionNumber, ipUnitySequenceNumber }
        STATUS      current
        DESCRIPTION " the ICM usage, as detected on the SCC, exceeds the desired threshold."
        ::= { ipUnityNotifications 292 }

ipUnityInterfaceHighUsage NOTIFICATION-TYPE
        OBJECTS  { ipUnityTrapSeverity, ipUnityCardIndex , ifIndex, ipUnityTrapInfoString, ipUnitySequenceNumber }
        STATUS      current
        DESCRIPTION " INTERFACE_HIGH_USAGE detected on an port in the SCC."
        ::= { ipUnityNotifications 297 }

ipUnityInterfaceHighError NOTIFICATION-TYPE
        OBJECTS  { ipUnityTrapSeverity, ipUnityCardIndex , ifIndex, ipUnityDirection, ipUnityTrapInfoString, ipUnitySequenceNumber }
        STATUS      current
        DESCRIPTION " INTERFACE_HIGH_ERROR is detected in the SCC."
        ::= { ipUnityNotifications 298 }

ipUnityIpError NOTIFICATION-TYPE
        OBJECTS  { ipUnityTrapSeverity, ipUnityCardIndex , ipUnityDirection, ipUnityTrapInfoString, ipUnitySequenceNumber }
        STATUS      current
        DESCRIPTION " IP_ERROR in the SCC."
        ::= { ipUnityNotifications 299 }

ipUnityUdpError NOTIFICATION-TYPE
        OBJECTS  { ipUnityTrapSeverity, ipUnityCardIndex , ipUnityDirection, ipUnityTrapInfoString, ipUnitySequenceNumber }
        STATUS      current
        DESCRIPTION " UDP_ERROR in the SCC."
        ::= { ipUnityNotifications 300 }

ipUnityPacketLoss NOTIFICATION-TYPE
        OBJECTS  { ipUnityTrapSeverity, ipUnityCardIndex , ipUnityTrapInfoString, ipUnitySequenceNumber }
        STATUS      current
        DESCRIPTION " Packet Loss detected on an port in the SCC."
        ::= { ipUnityNotifications 301 }

ipUnitySpmAtmSarInitFailure NOTIFICATION-TYPE
        OBJECTS  { ipUnityTrapSeverity, ipUnityCardIndex,ipUnityBankIndex, ipUnityTrapInfoString, ipUnitySequenceNumber }
        STATUS      current
        DESCRIPTION "a SPM Atm Sar Init Failure."
        ::= { ipUnityNotifications 302 }

ipUnitySpmFlash1CheckDisk   NOTIFICATION-TYPE
        OBJECTS  { ipUnityTrapSeverity, ipUnityCardIndex , ipUnityBankIndex, ipUnityTrapInfoString, ipUnitySequenceNumber }
        STATUS      current
        DESCRIPTION "a SPM Flash1 Checkdisk error."
        ::= { ipUnityNotifications 303 }

ipUnitySpmFlash2CheckDisk   NOTIFICATION-TYPE
        OBJECTS  { ipUnityTrapSeverity, ipUnityCardIndex , ipUnityBankIndex, ipUnityTrapInfoString, ipUnitySequenceNumber }
        STATUS      current
        DESCRIPTION "a SPM Flash2 Checkdisk error."
        ::= { ipUnityNotifications 304 }

ipUnitySpmFlash1InitFailure  NOTIFICATION-TYPE
        OBJECTS  { ipUnityTrapSeverity, ipUnityCardIndex , ipUnityBankIndex, ipUnityTrapInfoString, ipUnitySequenceNumber }
        STATUS      current
        DESCRIPTION " a SPM flash1 Init Failure."
        ::= { ipUnityNotifications 305 }

ipUnitySpmFlash2InitFailure  NOTIFICATION-TYPE
        OBJECTS  { ipUnityTrapSeverity, ipUnityCardIndex , ipUnityBankIndex, ipUnityTrapInfoString, ipUnitySequenceNumber }
        STATUS      current
        DESCRIPTION " a SPM flash1 Init Failure."
        ::= { ipUnityNotifications 306 }

ipUnityOdspAlternateImageBoot   NOTIFICATION-TYPE
        OBJECTS  { ipUnityTrapSeverity, ipUnityCardIndex, ipUnityBankIndex, ipUnityTrapInfoString, ipUnitySequenceNumber }
        STATUS      current
        DESCRIPTION "ODSP Alternate Image boot."
        ::= { ipUnityNotifications 307 }

ipUnitySpmAlternateImageBoot   NOTIFICATION-TYPE
        OBJECTS  { ipUnityTrapSeverity, ipUnityCardIndex, ipUnityBankIndex, ipUnityTrapInfoString, ipUnitySequenceNumber }
        STATUS      current
        DESCRIPTION "SPM Alternate Image boot."
        ::= { ipUnityNotifications 308 }

ipUnityOdspPIFCongestion   NOTIFICATION-TYPE
        OBJECTS  { ipUnityTrapSeverity, ipUnityCardIndex, ipUnityBankIndex, ipUnityTrapInfoString, ipUnitySequenceNumber }
        STATUS      current
        DESCRIPTION "ODSP PIF Congestion."
        ::= { ipUnityNotifications 309 }

ipUnitySpmPIFCongestion   NOTIFICATION-TYPE
        OBJECTS  { ipUnityTrapSeverity, ipUnityCardIndex, ipUnityBankIndex, ipUnityTrapInfoString, ipUnitySequenceNumber }
        STATUS      current
        DESCRIPTION "SPM PIF Congestion."
        ::= { ipUnityNotifications 310 }

ipUnitySCCILanInit   NOTIFICATION-TYPE
        OBJECTS  { ipUnityTrapSeverity, ipUnityCardIndex, ipUnityTrapInfoString, ipUnitySequenceNumber }
        STATUS      current
        DESCRIPTION "SCC ILan Init Failure."
        ::= { ipUnityNotifications 311 }

ipUnityOdspILanInit   NOTIFICATION-TYPE
        OBJECTS  { ipUnityTrapSeverity, ipUnityCardIndex, ipUnityBankIndex, ipUnityTrapInfoString, ipUnitySequenceNumber }
        STATUS      current
        DESCRIPTION "SCC ILan Init Failure."
        ::= { ipUnityNotifications 312 }

ipUnitySpmILanInit   NOTIFICATION-TYPE
        OBJECTS  { ipUnityTrapSeverity, ipUnityCardIndex, ipUnityBankIndex, ipUnityTrapInfoString, ipUnitySequenceNumber }
        STATUS      current
        DESCRIPTION "SPM ILan Init Failure."
        ::= { ipUnityNotifications 313 }

ipUnitySccFlash2AuditFailure   NOTIFICATION-TYPE
        OBJECTS  { ipUnityTrapSeverity, ipUnityCardIndex , ipUnityTrapInfoString, ipUnitySequenceNumber }
        STATUS      current
        DESCRIPTION "Flash2 Audit Failure."
        ::= { ipUnityNotifications 314 }

ipUnityTcpError NOTIFICATION-TYPE
        OBJECTS  { ipUnityTrapSeverity, ipUnityCardIndex , ipUnityDirection, ipUnityTrapInfoString, ipUnitySequenceNumber }
        STATUS      current
        DESCRIPTION " TCP_ERROR in the SCC."
        ::= { ipUnityNotifications 315 }

ipUnityAlarmCardError	NOTIFICATION-TYPE
	OBJECTS	{ ipUnityTrapSeverity, ipUnityCardIndex, ipUnityTrapInfoString, ipUnitySequenceNumber }
        STATUS      current
        DESCRIPTION " The Alarm Card Error ."
        ::= { ipUnityNotifications 316 }

ipUnitySccCardPowerUpFailure	NOTIFICATION-TYPE
	OBJECTS	{ ipUnityTrapSeverity, ipUnityCardIndex, ipUnityTrapInfoString, ipUnitySequenceNumber }
        STATUS      current
        DESCRIPTION " the SCC Card PowerUP Failure."
        ::= { ipUnityNotifications 317 }

ipUnitySccCardFailure	 NOTIFICATION-TYPE
        OBJECTS  { ipUnityTrapSeverity, ipUnityCardIndex, ipUnityTrapInfoString, ipUnitySequenceNumber }
        STATUS      current
        DESCRIPTION " a SCC Card Failure."
        ::= { ipUnityNotifications 318 }

ipUnitySccRecoveryFailure      NOTIFICATION-TYPE
        OBJECTS  { ipUnityTrapSeverity, ipUnityCardIndex,ipUnityCardType, ipUnityTrapInfoString, ipUnitySequenceNumber }
        STATUS      current
        DESCRIPTION " the SCC Recovery Failure."
        ::= { ipUnityNotifications 319 }

ipUnitySccLogFileNotFound	 NOTIFICATION-TYPE
        OBJECTS { ipUnityTrapSeverity, ipUnityCardIndex, ipUnityLogFileName, ipUnityTrapInfoString, ipUnitySequenceNumber }
        STATUS      current
        DESCRIPTION " the SCC log file not found trap."
        ::= { ipUnityNotifications 320 } 

ipUnitySccMessageQSendFailure	NOTIFICATION-TYPE
	OBJECTS	{ ipUnityTrapSeverity, ipUnityCardIndex, ipUnityTrapInfoString, ipUnitySequenceNumber }
        STATUS      current
        DESCRIPTION " the SCC message Q send Failure."
        ::= { ipUnityNotifications 321 }

ipUnitySccAnnInstNotFoundError	 NOTIFICATION-TYPE
        OBJECTS  { ipUnityTrapSeverity, ipUnityCardIndex, ipUnityTrapInfoString, ipUnitySequenceNumber }
        STATUS      current
        DESCRIPTION " a SCC Announcement Inst not found Error."
        ::= { ipUnityNotifications 322 }

ipUnitySccAnnDownloadFailure      NOTIFICATION-TYPE
        OBJECTS  { ipUnityTrapSeverity, ipUnityCardIndex,ipUnityCardType, ipUnityTrapInfoString, ipUnitySequenceNumber }
        STATUS      current
        DESCRIPTION " the SCC Ann Download Failure."
        ::= { ipUnityNotifications 323 }

ipUnityOdspBankReset  NOTIFICATION-TYPE
        OBJECTS  { ipUnityTrapSeverity, ipUnityCardIndex , ipUnityBankIndex, ipUnityTrapInfoString, ipUnitySequenceNumber }
        STATUS      current
        DESCRIPTION " ODSP Bank Reset trap."
        ::= { ipUnityNotifications 324 }

ipUnityOdspBankOOS  NOTIFICATION-TYPE
        OBJECTS  { ipUnityTrapSeverity, ipUnityCardIndex , ipUnityBankIndex, ipUnityTrapInfoString, ipUnitySequenceNumber }
        STATUS      current
        DESCRIPTION " a ODSP bank OOS trap."
        ::= { ipUnityNotifications 325 }

ipUnityOdspLogFileNotFound  NOTIFICATION-TYPE
        OBJECTS  { ipUnityTrapSeverity, ipUnityCardIndex , ipUnityBankIndex, ipUnityLogFileName, ipUnityTrapInfoString, ipUnitySequenceNumber }
        STATUS      current
        DESCRIPTION " ODSP log file not found trap."
        ::= { ipUnityNotifications 326 }

ipUnityOdspMessageQSendFailure  NOTIFICATION-TYPE
        OBJECTS  { ipUnityTrapSeverity, ipUnityCardIndex , ipUnityBankIndex, ipUnityTrapInfoString, ipUnitySequenceNumber }
        STATUS      current
        DESCRIPTION " a ODSP Messsage Q Send Failure."
        ::= { ipUnityNotifications 327 }

ipUnityOdspBankLowVoltage  NOTIFICATION-TYPE
        OBJECTS  { ipUnityTrapSeverity, ipUnityCardIndex , ipUnityBankIndex, ipUnityTrapInfoString, ipUnitySequenceNumber }
        STATUS      current
        DESCRIPTION " ODSP Bank low voltage."
        ::= { ipUnityNotifications 328 }

ipUnityOdspCpmOverload  NOTIFICATION-TYPE
        OBJECTS  { ipUnityTrapSeverity, ipUnityCardIndex , ipUnityBankIndex, ipUnityTrapInfoString, ipUnitySequenceNumber }
        STATUS      current
        DESCRIPTION " a ODSP Cpm overload."
        ::= { ipUnityNotifications 329 }

ipUnityOdspAnnInstrNotFound  NOTIFICATION-TYPE
        OBJECTS  { ipUnityTrapSeverity, ipUnityCardIndex , ipUnityBankIndex, ipUnityTrapInfoString, ipUnitySequenceNumber }
        STATUS      current
        DESCRIPTION " ODSP Ann instr not found error."
        ::= { ipUnityNotifications 330 }

ipUnitySpmBankReset  NOTIFICATION-TYPE
        OBJECTS  { ipUnityTrapSeverity, ipUnityCardIndex , ipUnityBankIndex, ipUnityTrapInfoString, ipUnitySequenceNumber }
        STATUS      current
        DESCRIPTION " SPM Bank Reset trap."
        ::= { ipUnityNotifications 331 }

ipUnitySpmBankOOS  NOTIFICATION-TYPE
        OBJECTS  { ipUnityTrapSeverity, ipUnityCardIndex , ipUnityBankIndex, ipUnityTrapInfoString, ipUnitySequenceNumber }
        STATUS      current
        DESCRIPTION " a SPM bank OOS trap."
        ::= { ipUnityNotifications 332 }

ipUnitySpmMemHighUsage  NOTIFICATION-TYPE
        OBJECTS  { ipUnityTrapSeverity, ipUnityCardIndex , ipUnityBankIndex, ipUnityTrapInfoString, ipUnitySequenceNumber }
        STATUS      current
        DESCRIPTION " SPM Memory High Usage."
        ::= { ipUnityNotifications 333 }

ipUnitySpmFSFailure  NOTIFICATION-TYPE
        OBJECTS  { ipUnityTrapSeverity, ipUnityCardIndex , ipUnityBankIndex, ipUnityTrapInfoString, ipUnitySequenceNumber }
        STATUS      current
        DESCRIPTION " a SPM FS Failure."
        ::= { ipUnityNotifications 334 }

ipUnitySpmFSHighUsage  NOTIFICATION-TYPE
        OBJECTS  { ipUnityTrapSeverity, ipUnityCardIndex , ipUnityBankIndex, ipUnityTrapInfoString, ipUnitySequenceNumber }
        STATUS      current
        DESCRIPTION " SPM FS High Usage."
        ::= { ipUnityNotifications 335 }

ipUnitySpmCommFailure  NOTIFICATION-TYPE
        OBJECTS  { ipUnityTrapSeverity, ipUnityCardIndex , ipUnityBankIndex, ipUnityTrapInfoString, ipUnitySequenceNumber }
        STATUS      current
        DESCRIPTION " a SPM Communication Failure."
        ::= { ipUnityNotifications 336 }

ipUnitySpmCpuHighUsageFailure  NOTIFICATION-TYPE
        OBJECTS  { ipUnityTrapSeverity, ipUnityCardIndex , ipUnityBankIndex, ipUnityTrapInfoString, ipUnitySequenceNumber }
        STATUS      current
        DESCRIPTION " SPM Cpu high Usage Failure."
        ::= { ipUnityNotifications 337 }

ipUnitySpmTaskSuspendFailure  NOTIFICATION-TYPE
        OBJECTS  { ipUnityTrapSeverity, ipUnityCardIndex , ipUnityBankIndex, ipUnityTaskName, ipUnityTrapInfoString, ipUnitySequenceNumber }
        STATUS      current
        DESCRIPTION " a SPM Task Suspend Failure."
        ::= { ipUnityNotifications 338 }

ipUnitySpmTaskResumeFailure  NOTIFICATION-TYPE
        OBJECTS  { ipUnityTrapSeverity, ipUnityCardIndex , ipUnityBankIndex, ipUnityTaskName, ipUnityTrapInfoString, ipUnitySequenceNumber }
        STATUS      current
        DESCRIPTION " a SPM Task Resume Failure."
        ::= { ipUnityNotifications 339 }

ipUnitySpmSoftwareException  NOTIFICATION-TYPE
        OBJECTS  { ipUnityTrapSeverity, ipUnityCardIndex , ipUnityBankIndex, ipUnityTrapInfoString, ipUnitySequenceNumber }
        STATUS      current
        DESCRIPTION " SPM Software Exception trap."
        ::= { ipUnityNotifications 340 }

ipUnitySpmSoftwareError  NOTIFICATION-TYPE
        OBJECTS  { ipUnityTrapSeverity, ipUnityCardIndex , ipUnityBankIndex, ipUnityTrapInfoString, ipUnitySequenceNumber }
        STATUS      current
        DESCRIPTION " SPM Software Error."
        ::= { ipUnityNotifications 341 }

ipUnitySpmDebugLogFull  NOTIFICATION-TYPE
        OBJECTS  { ipUnityTrapSeverity, ipUnityCardIndex , ipUnityBankIndex, ipUnityLogFileName, ipUnityTrapInfoString, ipUnitySequenceNumber }
        STATUS      current
        DESCRIPTION " SPM Debug Log Full."
        ::= { ipUnityNotifications 342 }

ipUnitySpmLogFileNotFound  NOTIFICATION-TYPE
        OBJECTS  { ipUnityTrapSeverity, ipUnityCardIndex , ipUnityBankIndex, ipUnityLogFileName, ipUnityTrapInfoString, ipUnitySequenceNumber }
        STATUS      current
        DESCRIPTION " SPM log file not found trap."
        ::= { ipUnityNotifications 343 }

ipUnitySpmMessageQSendFailure  NOTIFICATION-TYPE
        OBJECTS  { ipUnityTrapSeverity, ipUnityCardIndex , ipUnityBankIndex, ipUnityTrapInfoString, ipUnitySequenceNumber }
        STATUS      current
        DESCRIPTION " a SPM Messsage Q Send Failure."
        ::= { ipUnityNotifications 344 }

ipUnitySpmBankLowVoltage  NOTIFICATION-TYPE
        OBJECTS  { ipUnityTrapSeverity, ipUnityCardIndex , ipUnityBankIndex, ipUnityTrapInfoString, ipUnitySequenceNumber }
        STATUS      current
        DESCRIPTION " SPM Bank low voltage."
        ::= { ipUnityNotifications 345 }

ipUnitySpmCpmOverload  NOTIFICATION-TYPE
        OBJECTS  { ipUnityTrapSeverity, ipUnityCardIndex , ipUnityBankIndex, ipUnityTrapInfoString, ipUnitySequenceNumber }
        STATUS      current
        DESCRIPTION " a SPM cpm overload."
        ::= { ipUnityNotifications 346 }

ipUnitySpmAnnInstrNotFound  NOTIFICATION-TYPE
        OBJECTS  { ipUnityTrapSeverity, ipUnityCardIndex , ipUnityBankIndex, ipUnityTrapInfoString, ipUnitySequenceNumber }
        STATUS      current
        DESCRIPTION " SPM Ann instr not found error."
        ::= { ipUnityNotifications 347 }

ipUnitySpmUpgradeFailure        NOTIFICATION-TYPE
        OBJECTS  { ipUnityTrapSeverity, ipUnityCardIndex, ipUnityBankIndex, ipUnityTrapInfoString, ipUnitySequenceNumber }
        STATUS      current
        DESCRIPTION " the upgrade of the SPM image fails."
        ::= { ipUnityNotifications 348 }

ipUnitySpmVersionMismatch       NOTIFICATION-TYPE
        OBJECTS  { ipUnityTrapSeverity, ipUnityCardIndex, ipUnityBankIndex, ipUnityTrapInfoString, ipUnitySequenceNumber }
        STATUS      current
        DESCRIPTION " the SPM version mismatch occurs."
        ::= { ipUnityNotifications 349 }

ipUnitySpmAnnDownloadFailure        NOTIFICATION-TYPE
        OBJECTS  { ipUnityTrapSeverity, ipUnityCardIndex, ipUnityBankIndex, ipUnityTrapInfoString, ipUnitySequenceNumber }
        STATUS      current
        DESCRIPTION " the SPM Announcement Download Failure."
        ::= { ipUnityNotifications 350 }

ipUnitySpmDuplicateAnnouncement       NOTIFICATION-TYPE
        OBJECTS  { ipUnityTrapSeverity, ipUnityCardIndex, ipUnityBankIndex, ipUnityTrapInfoString, ipUnitySequenceNumber }
        STATUS      current
        DESCRIPTION " the SPM Duplicate Announcement trap."
        ::= { ipUnityNotifications 351 }

ipUnityDspModuleMemHighUsage		NOTIFICATION-TYPE
        OBJECTS  { ipUnityTrapSeverity, ipUnityCardIndex , ipUnityBankIndex, ipUnityModuleIndex, ipUnityTrapInfoString, ipUnitySequenceNumber }
        STATUS      current
        DESCRIPTION " Dsp Module Memory High Usage."
        ::= { ipUnityNotifications 352 }

ipUnityDspModuleNFSRevQFull		NOTIFICATION-TYPE
        OBJECTS  { ipUnityTrapSeverity, ipUnityCardIndex , ipUnityBankIndex, ipUnityModuleIndex, ipUnityTrapInfoString, ipUnitySequenceNumber }
        STATUS      current
        DESCRIPTION "  a DSP Module NFS Rev Q Full Error."
        ::= { ipUnityNotifications 353 }

ipUnityDspModuleUpgradeFailure        NOTIFICATION-TYPE
        OBJECTS  { ipUnityTrapSeverity, ipUnityCardIndex, ipUnityBankIndex, ipUnityModuleIndex, ipUnityTrapInfoString, ipUnitySequenceNumber }
        STATUS      current
        DESCRIPTION " the upgrade of the DSP image fails."
        ::= { ipUnityNotifications 354 }

ipUnityDspModuleVersionMismatch       NOTIFICATION-TYPE
        OBJECTS  { ipUnityTrapSeverity, ipUnityCardIndex, ipUnityBankIndex, ipUnityModuleIndex, ipUnityTrapInfoString, ipUnitySequenceNumber }
        STATUS      current
        DESCRIPTION " the DSP version mismatch occurs."
        ::= { ipUnityNotifications 355 }

ipUnityDspModuleChannelNoRTP		NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION "  a DSP in the bank cannot send or receive RTP data."
        ::= { ipUnityNotifications 356 }

ipUnityDspModuleChannelPayloadMismatch	 NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " a payload mismatch is detected in a channel belonging to a DSP."
        ::= { ipUnityNotifications 357 }

ipUnityDspModuleChannelCPMTXFailure	 NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " a CPM transmission failure detected in a channel belonging to a DSP."
        ::= { ipUnityNotifications 358 }

ipUnityDspModuleLongDurationCall        NOTIFICATION-TYPE
        OBJECTS  { ipUnityTrapSeverity, ipUnityCardIndex, ipUnityBankIndex, ipUnityModuleIndex, ipUnityTrapInfoString, ipUnitySequenceNumber }
        STATUS      current
        DESCRIPTION " the DSP long duration call error."
        ::= { ipUnityNotifications 359 }

ipUnityDspModuleHungCall        NOTIFICATION-TYPE
        OBJECTS  { ipUnityTrapSeverity, ipUnityCardIndex, ipUnityBankIndex, ipUnityModuleIndex, ipUnityTrapInfoString, ipUnitySequenceNumber }
        STATUS      current
        DESCRIPTION " the DSP Hung call error."
        ::= { ipUnityNotifications 360 }

ipUnityDspModuleChannelLockout	 NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " a  lockout detected in a channel belonging to a DSP."
        ::= { ipUnityNotifications 361 }

ipUnitySpmG4ModuleLock        NOTIFICATION-TYPE
        OBJECTS  { ipUnityTrapSeverity, ipUnityCardIndex, ipUnityBankIndex, ipUnityModuleIndex, ipUnityTrapInfoString, ipUnitySequenceNumber }
        STATUS      current
        DESCRIPTION " the Lock detected in the SPMG4 module."
        ::= { ipUnityNotifications 362 }

ipUnitySpmG4ModuleOOServ        NOTIFICATION-TYPE
        OBJECTS  { ipUnityTrapSeverity, ipUnityCardIndex, ipUnityBankIndex, ipUnityModuleIndex, ipUnityTrapInfoString, ipUnitySequenceNumber }
        STATUS      current
        DESCRIPTION " SPMG4 module error."
        ::= { ipUnityNotifications 363 }

ipUnitySpmG4ModuleSoftInit        NOTIFICATION-TYPE
        OBJECTS  { ipUnityTrapSeverity, ipUnityCardIndex, ipUnityBankIndex, ipUnityModuleIndex, ipUnityTrapInfoString, ipUnitySequenceNumber }
        STATUS      current
        DESCRIPTION " the Software Init failure in the SPMG4."
        ::= { ipUnityNotifications 364 }

ipUnitySpmG4ModuleMemHighUsage        NOTIFICATION-TYPE
        OBJECTS  { ipUnityTrapSeverity, ipUnityCardIndex, ipUnityBankIndex, ipUnityModuleIndex, ipUnityTrapInfoString, ipUnitySequenceNumber }
        STATUS      current
        DESCRIPTION " SPMG4 Memory High usage error."
        ::= { ipUnityNotifications 365 }

ipUnitySpmG4ModuleInitFailure        NOTIFICATION-TYPE
        OBJECTS  { ipUnityTrapSeverity, ipUnityCardIndex, ipUnityBankIndex, ipUnityModuleIndex, ipUnityTrapInfoString, ipUnitySequenceNumber }
        STATUS      current
        DESCRIPTION " the Init failure in the SPMG4."
        ::= { ipUnityNotifications 366 }

ipUnitySpmG4ModuleCommFailure        NOTIFICATION-TYPE
        OBJECTS  { ipUnityTrapSeverity, ipUnityCardIndex, ipUnityBankIndex, ipUnityModuleIndex, ipUnityTrapInfoString, ipUnitySequenceNumber }
        STATUS      current
        DESCRIPTION " SPMG4 Communication Failure error."
        ::= { ipUnityNotifications 367 }

ipUnitySpmG4ModuleCpuHighUsageFailure  NOTIFICATION-TYPE
        OBJECTS  { ipUnityTrapSeverity, ipUnityCardIndex , ipUnityBankIndex, ipUnityModuleIndex, ipUnityTrapInfoString, ipUnitySequenceNumber }
        STATUS      current
        DESCRIPTION " SPMG4 Cpu high Usage Failure."
        ::= { ipUnityNotifications 368 }

ipUnitySpmG4ModuleTaskSuspendFailure  NOTIFICATION-TYPE
        OBJECTS  { ipUnityTrapSeverity, ipUnityCardIndex , ipUnityBankIndex, ipUnityModuleIndex, ipUnityTaskName, ipUnityTrapInfoString, ipUnitySequenceNumber }
        STATUS      current
        DESCRIPTION " a SPMG4 Task Suspend Failure."
        ::= { ipUnityNotifications 369 }

ipUnitySpmG4ModuleTaskResumeFailure  NOTIFICATION-TYPE
        OBJECTS  { ipUnityTrapSeverity, ipUnityCardIndex , ipUnityBankIndex, ipUnityModuleIndex, ipUnityTaskName, ipUnityTrapInfoString, ipUnitySequenceNumber }
        STATUS      current
        DESCRIPTION " a SPMG4 Task Resume Failure."
        ::= { ipUnityNotifications 370 }

ipUnitySpmG4ModuleSoftwareException  NOTIFICATION-TYPE
        OBJECTS  { ipUnityTrapSeverity, ipUnityCardIndex , ipUnityBankIndex, ipUnityModuleIndex, ipUnityTrapInfoString, ipUnitySequenceNumber }
        STATUS      current
        DESCRIPTION " SPMG4 Software Exception trap."
        ::= { ipUnityNotifications 371 }

ipUnitySpmG4ModuleSoftwareError  NOTIFICATION-TYPE
        OBJECTS  { ipUnityTrapSeverity, ipUnityCardIndex , ipUnityBankIndex, ipUnityModuleIndex, ipUnityTrapInfoString, ipUnitySequenceNumber }
        STATUS      current
        DESCRIPTION " SPMG4 Software Error."
        ::= { ipUnityNotifications 372 }

ipUnitySpmG4ModuleDebugLogFull  NOTIFICATION-TYPE
        OBJECTS  { ipUnityTrapSeverity, ipUnityCardIndex , ipUnityBankIndex, ipUnityModuleIndex, ipUnityLogFileName, ipUnityTrapInfoString, ipUnitySequenceNumber }
        STATUS      current
        DESCRIPTION " SPMG4 Debug Log Full."
        ::= { ipUnityNotifications 373 }

ipUnitySpmG4ModuleLogFileNotFound  NOTIFICATION-TYPE
        OBJECTS  { ipUnityTrapSeverity, ipUnityCardIndex , ipUnityBankIndex, ipUnityModuleIndex, ipUnityLogFileName, ipUnityTrapInfoString, ipUnitySequenceNumber }
        STATUS      current
        DESCRIPTION " SPMG4 log file not found trap."
        ::= { ipUnityNotifications 374 }

ipUnitySpmG4ModuleMessageQSendFailure  NOTIFICATION-TYPE
        OBJECTS  { ipUnityTrapSeverity, ipUnityCardIndex , ipUnityBankIndex, ipUnityModuleIndex, ipUnityTrapInfoString, ipUnitySequenceNumber }
        STATUS      current
        DESCRIPTION " a SPMG4 Messsage Q Send Failure."
        ::= { ipUnityNotifications 375 }

ipUnitySpmG4ModuleMgcpError  NOTIFICATION-TYPE
        OBJECTS  { ipUnityTrapSeverity, ipUnityCardIndex , ipUnityBankIndex, ipUnityModuleIndex, ipUnityTrapInfoString, ipUnitySequenceNumber }
        STATUS      current
        DESCRIPTION " SPMG4 Mgcp error."
        ::= { ipUnityNotifications 376 }

ipUnitySpmG4ModuleIcmAsrSocketFailure  NOTIFICATION-TYPE
        OBJECTS  { ipUnityTrapSeverity, ipUnityCardIndex , ipUnityBankIndex, ipUnityModuleIndex, ipUnityTrapInfoString, ipUnitySequenceNumber }
        STATUS      current
        DESCRIPTION " SPMG4 Icm Asr Socket Failure."
        ::= { ipUnityNotifications 377 }

ipUnitySpmG4ModuleIcmTtsSocketFailure  NOTIFICATION-TYPE
        OBJECTS  { ipUnityTrapSeverity, ipUnityCardIndex , ipUnityBankIndex, ipUnityModuleIndex, ipUnityTrapInfoString, ipUnitySequenceNumber }
        STATUS      current
        DESCRIPTION " a SPMG4 Icm TTS  Socket Failure."
        ::= { ipUnityNotifications 378 }

ipUnitySpmG4ModuleUpgradeFailure        NOTIFICATION-TYPE
        OBJECTS  { ipUnityTrapSeverity, ipUnityCardIndex, ipUnityBankIndex, ipUnityModuleIndex, ipUnityTrapInfoString, ipUnitySequenceNumber }
        STATUS      current
        DESCRIPTION " the upgrade of the SPMG4 image fails."
        ::= { ipUnityNotifications 379 }

ipUnitySpmG4ModuleVersionMismatch       NOTIFICATION-TYPE
        OBJECTS  { ipUnityTrapSeverity, ipUnityCardIndex, ipUnityBankIndex, ipUnityModuleIndex, ipUnityTrapInfoString, ipUnitySequenceNumber }
        STATUS      current
        DESCRIPTION " the SpmG4 version mismatch occurs."
        ::= { ipUnityNotifications 380 }

ipUnitySpmG4ModuleNoInterface       NOTIFICATION-TYPE
        OBJECTS  { ipUnityTrapSeverity, ipUnityCardIndex, ipUnityBankIndex, ipUnityModuleIndex, ipUnityTrapInfoString, ipUnitySequenceNumber }
        STATUS      current
        DESCRIPTION " the SpmG4 No Interface."
        ::= { ipUnityNotifications 381 }

ipUnitySpmG4ModuleNoRoute		NOTIFICATION-TYPE
        OBJECTS  { ipUnityTrapSeverity, ipUnityCardIndex , ipUnityBankIndex, ipUnityModuleIndex, ifIndex, ipUnityTrapInfoString, ipUnitySequenceNumber }
        STATUS      current
        DESCRIPTION "  a SPMG4 no route error."
        ::= { ipUnityNotifications 382 }

ipUnitySpmG4ModuleInterfaceHighError		NOTIFICATION-TYPE
        OBJECTS  { ipUnityTrapSeverity, ipUnityCardIndex , ipUnityBankIndex, ipUnityModuleIndex, ifIndex, ipUnityTrapInfoString, ipUnitySequenceNumber }
        STATUS      current
        DESCRIPTION "  a SPMG4 Interface High error."
        ::= { ipUnityNotifications 383 } 

ipUnityRadiusUnreachable                NOTIFICATION-TYPE
        OBJECTS { ipUnityTrapSeverity, ipUnityIpAddress, ipUnityTrapInfoString, ipUnitySequenceNumber }
        STATUS     current
        DESCRIPTION "Unable to contact the radius server."
        ::= {ipUnityNotifications 384 }

ipUnityLoginFailure                     NOTIFICATION-TYPE
        OBJECTS {ipUnityTrapSeverity, ipUnityLoginName, ipUnityTrapInfoString, ipUnitySequenceNumber }
        STATUS     current
        DESCRIPTION "This information alarm is generated when user failed to login after max number of retries."
        ::= {ipUnityNotifications 385 }

ipUnityAccountExpired                   NOTIFICATION-TYPE
        OBJECTS {ipUnityTrapSeverity, ipUnityLoginName, ipUnityTrapInfoString, ipUnitySequenceNumber }
        STATUS     current
        DESCRIPTION "Indicates the account is expired."
        ::= {ipUnityNotifications 386 }

ipUnityAnnInstFileInvalidFormat          NOTIFICATION-TYPE
        OBJECTS  { ipUnityTrapSeverity, ipUnityCardIndex, ipUnityTrapInfoString, ipUnitySequenceNumber }
        STATUS      current
        DESCRIPTION "Announcement Instruction File Invalid format." 
        ::= { ipUnityNotifications 387 }

ipUnitySccCallProcOverload     NOTIFICATION-TYPE
        OBJECTS { ipUnityTrapSeverity, ipUnityCardIndex, ipUnityTrapInfoString, ipUnitySequenceNumber }
        STATUS      current
        DESCRIPTION " Call process overload error."
        ::= { ipUnityNotifications 388 }

ipUnitySpmG4ModuleCallProcOverload     NOTIFICATION-TYPE
        OBJECTS { ipUnityTrapSeverity, ipUnityCardIndex, ipUnityBankIndex, ipUnityModuleIndex, ipUnityTrapInfoString, ipUnitySequenceNumber }
        STATUS      current
        DESCRIPTION " Call process overload error."
        ::= { ipUnityNotifications 389 }

ipUnitySccMegacoError     NOTIFICATION-TYPE
        OBJECTS { ipUnityTrapSeverity, ipUnityCardIndex, ipUnityTrapInfoString, ipUnitySequenceNumber }
        STATUS      current
        DESCRIPTION " SCC MEGACO error."
        ::= { ipUnityNotifications 390 }

ipUnitySpmG4ModuleMegacoError  NOTIFICATION-TYPE
        OBJECTS  { ipUnityTrapSeverity, ipUnityCardIndex , ipUnityBankIndex, ipUnityModuleIndex, ipUnityTrapInfoString, ipUnitySequenceNumber }
        STATUS      current
        DESCRIPTION " SPMG4 Megaco error."
        ::= { ipUnityNotifications 391 }

ipUnityDspModuleVedioFrameBad	 NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " Vedio frame bad error."
        ::= { ipUnityNotifications 392 }

ipUnityDspModuleVedioExceedMdi	 NOTIFICATION-TYPE
        OBJECTS  { ipUnityTrapSeverity, ipUnityCardIndex , ipUnityBankIndex, ipUnityModuleIndex, ipUnityChannelIndex, ipUnityTrapInfoString, ipUnitySequenceNumber }
        STATUS      current
        DESCRIPTION " Vedio Exceed Mdi." 
        ::= { ipUnityNotifications 393 }

ipUnityOdsp3BankOOS  NOTIFICATION-TYPE
        OBJECTS  { ipUnityTrapSeverity, ipUnityCardIndex , ipUnityBankIndex, ipUnityTrapInfoString, ipUnitySequenceNumber }
        STATUS      current
        DESCRIPTION " a ODSP 3 bank OOS trap."
        ::= { ipUnityNotifications 394 }

ipUnityMpc20CardPowerUpFailure	NOTIFICATION-TYPE
	OBJECTS	{ ipUnityTrapSeverity, ipUnityCardIndex, ipUnityTrapInfoString, ipUnitySequenceNumber }
        STATUS      current
        DESCRIPTION " the MPC20 Card PowerUP Failure."
        ::= { ipUnityNotifications 395 }

ipUnityMpc20Flash1InitFailure  NOTIFICATION-TYPE
        OBJECTS  { ipUnityTrapSeverity, ipUnityCardIndex, ipUnityTrapInfoString, ipUnitySequenceNumber }
        STATUS      current
        DESCRIPTION " a MPC20 flash1 Init Failure."
        ::= { ipUnityNotifications 396 }

ipUnityMpc20Flash2InitFailure  NOTIFICATION-TYPE
        OBJECTS  { ipUnityTrapSeverity, ipUnityCardIndex, ipUnityTrapInfoString, ipUnitySequenceNumber }
        STATUS      current
        DESCRIPTION " a MPC20 flash2 Init Failure."
        ::= { ipUnityNotifications 397 }

ipUnityMpc20Flash1CheckDisk   NOTIFICATION-TYPE
        OBJECTS  { ipUnityTrapSeverity, ipUnityCardIndex , ipUnityTrapInfoString, ipUnitySequenceNumber }
        STATUS      current
        DESCRIPTION "Flash1 Checkdisk error."
        ::= { ipUnityNotifications 398 }
        
ipUnityMpc20Flash2CheckDisk   NOTIFICATION-TYPE
        OBJECTS  { ipUnityTrapSeverity, ipUnityCardIndex , ipUnityTrapInfoString, ipUnitySequenceNumber }
        STATUS      current
        DESCRIPTION "Flash2 Checkdisk error."
        ::= { ipUnityNotifications 399 }
        
ipUnityMpc20Flash1AuditFailure   NOTIFICATION-TYPE
        OBJECTS  { ipUnityTrapSeverity, ipUnityCardIndex, ipUnityTrapInfoString, ipUnitySequenceNumber }
        STATUS      current
        DESCRIPTION "MPC20 Flash1 Audit Failure."
        ::= { ipUnityNotifications 400 }

ipUnityMpc20Flash2AuditFailure   NOTIFICATION-TYPE
        OBJECTS  { ipUnityTrapSeverity, ipUnityCardIndex, ipUnityTrapInfoString, ipUnitySequenceNumber }
        STATUS      current
        DESCRIPTION "MPC20 Flash2 Audit Failure."
        ::= { ipUnityNotifications 401 }

ipUnityMpc20MemHighUsage  NOTIFICATION-TYPE
        OBJECTS  { ipUnityTrapSeverity, ipUnityCardIndex, ipUnityTrapInfoString, ipUnitySequenceNumber }
        STATUS      current
        DESCRIPTION "MPC20 Memory High Usage."
        ::= { ipUnityNotifications 402 }

ipUnityMpc20CardFailure	 NOTIFICATION-TYPE
        OBJECTS  { ipUnityTrapSeverity, ipUnityCardIndex, ipUnityTrapInfoString, ipUnitySequenceNumber }
        STATUS      current
        DESCRIPTION " a MPC20 Card Failure."
        ::= { ipUnityNotifications 403 }

ipUnityMpc20InitFailure  NOTIFICATION-TYPE
        OBJECTS  { ipUnityTrapSeverity, ipUnityCardIndex , ipUnityBankIndex, ipUnityTrapInfoString, ipUnitySequenceNumber }
        STATUS      current
        DESCRIPTION " a MPC20 Init Failure."
        ::= { ipUnityNotifications 404 }

ipUnityMpc20I2CInitFailure NOTIFICATION-TYPE
    OBJECTS { ipUnityTrapSeverity, ipUnityCardIndex, ipUnityTrapInfoString, ipUnitySequenceNumber }
        STATUS      current
        DESCRIPTION " the I2C Init failure."
        ::= { ipUnityNotifications 405 }

ipUnityMpc20CommFailure  NOTIFICATION-TYPE
        OBJECTS  { ipUnityTrapSeverity, ipUnityCardIndex, ipUnityTrapInfoString, ipUnitySequenceNumber }
        STATUS      current
        DESCRIPTION " a MPC20 Communication Failure."
        ::= { ipUnityNotifications 406 }

ipUnityMpc20CpuOverload	NOTIFICATION-TYPE
	OBJECTS	{ ipUnityTrapSeverity, ipUnityCardIndex, ipUnityTrapInfoString, ipUnitySequenceNumber }
        STATUS      current
        DESCRIPTION " the CPU usage is high in the MPC20 ."
        ::= { ipUnityNotifications 407 }

ipUnityMpc20TaskSuspended	 NOTIFICATION-TYPE
        OBJECTS  { ipUnityTrapSeverity, ipUnityCardIndex, ipUnityTaskName, ipUnityTrapInfoString, ipUnitySequenceNumber }
        STATUS      current
        DESCRIPTION " a task in the MPC20 gets suspended."
        ::= { ipUnityNotifications 408 }

ipUnityMpc20TaskResumeFailed	NOTIFICATION-TYPE
        OBJECTS  { ipUnityTrapSeverity, ipUnityCardIndex , ipUnityTaskName, ipUnityTrapInfoString, ipUnitySequenceNumber }
        STATUS      current
        DESCRIPTION " a task resumption fails in the MPC20."
        ::= { ipUnityNotifications 409 }

ipUnityMpc20DebugLogFull	NOTIFICATION-TYPE
        OBJECTS  { ipUnityTrapSeverity, ipUnityCardIndex , ipUnityLogFileName, ipUnityTrapInfoString, ipUnitySequenceNumber }
        STATUS      current
        DESCRIPTION " the logging media is full in the MPC20."
        ::= { ipUnityNotifications 410 }

ipUnityMpc20LogFileNotFound  NOTIFICATION-TYPE
        OBJECTS  { ipUnityTrapSeverity, ipUnityCardIndex , ipUnityLogFileName, ipUnityTrapInfoString, ipUnitySequenceNumber }
        STATUS      current
        DESCRIPTION " MPC20 log file not found trap."
        ::= { ipUnityNotifications 411 }

ipUnityMpc20MessageQSendFailure  NOTIFICATION-TYPE
        OBJECTS  { ipUnityTrapSeverity, ipUnityCardIndex , ipUnityTrapInfoString, ipUnitySequenceNumber }
        STATUS      current
        DESCRIPTION " a MPC20 Messsage Q Send Failure."
        ::= { ipUnityNotifications 412 }

ipUnityMpc20AlternateImageBoot   NOTIFICATION-TYPE
        OBJECTS  { ipUnityTrapSeverity, ipUnityCardIndex, ipUnityTrapInfoString, ipUnitySequenceNumber }
        STATUS      current
        DESCRIPTION "MPC20 Alternate Image boot."
        ::= { ipUnityNotifications 413 }

ipUnityMpc20ILanInit   NOTIFICATION-TYPE
        OBJECTS  { ipUnityTrapSeverity, ipUnityCardIndex, ipUnityTrapInfoString, ipUnitySequenceNumber }
        STATUS      current
        DESCRIPTION "MPC20 ILan Init Failure."
        ::= { ipUnityNotifications 414 }

ipUnityMpc20BankLowVoltage  NOTIFICATION-TYPE
        OBJECTS  { ipUnityTrapSeverity, ipUnityCardIndex , ipUnityBankIndex, ipUnityTrapInfoString, ipUnitySequenceNumber }
        STATUS      current
        DESCRIPTION " MPC20 Bank low voltage."
        ::= { ipUnityNotifications 415 }

ipUnityMpc20CpmOverload  NOTIFICATION-TYPE
        OBJECTS  { ipUnityTrapSeverity, ipUnityCardIndex , ipUnityTrapInfoString, ipUnitySequenceNumber }
        STATUS      current
        DESCRIPTION " a MPC20 cpm overload."
        ::= { ipUnityNotifications 416 }

ipUnityMpc20UpgradeFailure        NOTIFICATION-TYPE
        OBJECTS  { ipUnityTrapSeverity, ipUnityCardIndex, ipUnityTrapInfoString, ipUnitySequenceNumber }
        STATUS      current
        DESCRIPTION " the upgrade of the MPC20 image fails."
        ::= { ipUnityNotifications 417 }

ipUnityMpc20VersionMismatch       NOTIFICATION-TYPE
        OBJECTS  { ipUnityTrapSeverity, ipUnityCardIndex, ipUnityTrapInfoString, ipUnitySequenceNumber }
        STATUS      current
        DESCRIPTION " the MPC20 version mismatch occurs."
        ::= { ipUnityNotifications 418 }
END
