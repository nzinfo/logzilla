-- MIB file created 10-Jan-2007 13:33:54, by
--   SMICng version 2.2.11-beta(PRO)(Solaris), January 20, 2001. Enterprise key cisco.com

OLD-CISCO-CHASSIS-MIB DEFINITIONS ::= BEGIN

-- From file: "OLD-CISCO-CHASSIS-MIB.my"
-- Compile options "4 7 F H N O W 03 06 0B 0G 0N 0T"

IMPORTS
    TimeTicks
            FROM RFC1155-SMI
    OBJECT-TYPE
            FROM RFC-1212
    DisplayString
            FROM RFC1213-MIB
    temporary
            FROM CISCO-SMI;

chassis         OBJECT IDENTIFIER ::= { temporary 6 }

chassisType OBJECT-TYPE
    SYNTAX INTEGER {
        unknown(1),
        multibus(2),
        agsplus(3),
        igs(4),
        c2000(5),
        c3000(6),
        c4000(7),
        c7000(8),
        cs500(9),
        c7010(10),
        c2500(11),
        c4500(12),
        c2102(13),
        c2202(14),
        c2501(15),
        c2502(16),
        c2503(17),
        c2504(18),
        c2505(19),
        c2506(20),
        c2507(21),
        c2508(22),
        c2509(23),
        c2510(24),
        c2511(25),
        c2512(26),
        c2513(27),
        c2514(28),
        c2515(29),
        c3101(30),
        c3102(31),
        c3103(32),
        c3104(33),
        c3202(34),
        c3204(35),
        accessProRC(36),
        accessProEC(37),
        c1000(38),
        c1003(39),
        c1004(40),
        c2516(41),
        c7507(42),
        c7513(43),
        c7506(44),
        c7505(45),
        c1005(46),
        c4700(47),
        c2517(48),
        c2518(49),
        c2519(50),
        c2520(51),
        c2521(52),
        c2522(53),
        c2523(54),
        c2524(55),
        c2525(56),
        c4700S(57),
        c7206(58),
        c3640(59),
        as5200(60),
        c1601(61),
        c1602(62),
        c1603(63),
        c1604(64),
        c7204(65),
        c3620(66),
        wsx3011(68),
        mc3810(69),
        c1503(72),
        as5300(73),
        as2509RJ(74),
        as2511RJ(75),
        c2501FRADFX(77),
        c2501LANFRADFX(78),
        c2502LANFRADFX(79),
        wsx5302(80),
        c1605(81),
        c12012(82),
        c12008(85),
        ubr7246(86),
        c2610(87),
        c2612(88),
        c2611(89),
        ubr904(90),
        c6200(91),
        c3660(92),
        c7202(94),
        c2620(95),
        c2621(96),
        rpm(99),
        c1710(100),
        c1720(101),
        c7576(102),
        c1401(103),
        c2613(104),
        ubr7223(105),
        c6400Nrp(106),
        c801(107),
        c802(108),
        c803(109),
        c804(110),
        c7206VXR(111),
        c7204VXR(112),
        c1750(113),
        mgx8850(114),
        c805(116),
        ws-c3508g-xl(117),
        ws-c3512-xl(118),
        ws-c3524-xl(119),
        ws-c2908-xl(120),
        ws-c2916m-xl(121),
        ws-c2924-xl-v(122),
        ws-c2924c-xl-v(123),
        ws-c2912-xl(124),
        ws-c2924m-xl(125),
        ws-c2912mf-xl(126),
        c1417(128),
        cOpticalRegenerator(129),
        ws-c2924-xl(130),
        ws-c2924c-xl(131),
        ubr924(132),
        ws-x6302-msm(133),
        cat5k-rsfc(134),
        c7120-quadt1(136),
        c7120-t3(137),
        c7120-e3(138),
        c7120-at3(139),
        c7120-ae3(140),
        c7120-smi3(141),
        c7140-dualt3(142),
        c7140-duale3(143),
        c7140-dualat3(144),
        c7140-dualae3(145),
        c7140-dualmm3(146),
        c12016(150),
        c7140-octt1(152),
        c7140-dualfe(153),
        cat3548xl(154),
        cat6006(155),
        cat6009(156),
        cat6506(157),
        cat6509(158),
        mc3810-v3(160),
        c7507z(162),
        c7513z(163),
        c7507mx(164),
        c7513mx(165),
        ubr912-c(166),
        ubr912-s(167),
        ubr914(168),
        cat4232-l3(173),
        cOpticalRegeneratorDCPower(174),
        cva122(180),
        cva124(181),
        as5850(182),
        mgx8240(185),
        ubr925(191),
        ubr10012(192),
        c12016-8r(194),
        c2650(195),
        c2651(196),
        c1751(202),
        c626(205),
        c627(206),
        c633(207),
        c673(208),
        c675(209),
        c675e(210),
        c676(211),
        c677(212),
        c678(213),
        c3661-ac(214),
        c3661-dc(215),
        c3662-ac(216),
        c3662-dc(217),
        c3662-ac-co(218),
        c3662-dc-co(219),
        ubr7111(220),
        ubr7114(222),
        c12010(224),
        c8110(225),
        ubr905(227),
        c7150-dualfe(231),
        c7150-octt1(232),
        c7150-dualt3(233),
        cvps1110(236),
        ccontentengine(237),
        ciad2420(238),
        c677i(239),
        c674(240),
        cdpa7630(241),
        cat2924-lre-xl(245),
        cat2912-lre-xl(246),
        cva122e(247),
        cva124e(248),
        curm(249),
        curm2fe(250),
        curm2fe2v(251),
        c7401VXR(252),
        cap340(255),
        cap350(256),
        cdpa7610(257),
        c12416(261),
        ws-c2948g-l3-dc(262),
        ws-c4908g-l3-dc(263),
        c12406(264),
        pix-firewall506(265),
        pix-firewall515(266),
        pix-firewall520(267),
        pix-firewall525(268),
        pix-firewall535(269),
        c12410(270),
        c811(271),
        c813(272),
        c10720(273),
        cMWR1900(274),
        c4224(275),
        cWSC6513(276),
        c7603(277),
        c7606(278),
        c7401ASR(279),
        cVG248(280),
        c1105(281),
        cCe507(284),
        cCe560(285),
        cCe590(286),
        cCe7320(287),
        c2691(288),
        c3725(289),
        c1760(291),
        pix-firewall501(292),
        c2610M(293),
        c2611M(294),
        c12404(298),
        c9004(299),
        cCe507av(307),
        cCe560av(308),
        cIe2105(309),
        c7304(313),
        cWSC6503(322),
        ccontentengine2636(326),
        ccontentengine-dw2636(327),
        c6400-uac(332),
        c2610XM(334),
        c2611XM(335),
        c2620XM(336),
        c2621XM(337),
        c2650XM(338),
        c2651XM(339),
        cat295024sx(350),
        as5400-hpx(353),
        c7609(365),
        cMWR1941DC(371),
        cVG200(372),
        airap1210(373),
        cat375048PS(374),
        c7613(377),
        airbr-1410(380),
        cWSC6509neba(381),
        c1701(384),
        cat29408TT(385),
        cat29408TF(386),
        airap350ios(394),
        cat295024-lre-st-997(396),
        cat6k-sup720(400),
        airbr-1300(404),
        c878(410),
        c871(411),
        c2811(413),
        c2821(414),
        c2851(415),
        cat3750g-16td(420),
        cigesm(422),
        c1841(423),
        c2801(424),
        cds-x9132-k9(430),
        cds-x9116-k9(431),
        cat3560G24-ps(432),
        cat3560G24-ts(433),
        cat3560G48-ps(434),
        cat3560G48-ts(435),
        cds-c9216i-k9(436),
        airap-1130(439),
        c7604(440),
        c371098-hp-001(443),
        cat356024-ts(447),
        cat356048-ts(448),
        cwlse1130(454),
        cwlse1030(455),
        cids4210(457),
        cids4215(458),
        cids4235(459),
        cids4240(460),
        cids4250(461),
        cids4250sx(462),
        cids4250xl(463),
        cids4255(464),
        cWSC6504E(466),
        cfe-6326-k9(468),
        dsC9120ClK9(471),
        cat6k-msfc2a(481),
        cme6340aca(482),
        cme6340dca(483),
        cme6340dcb(484),
        nm-16es-1ge(493),
        nm-x-24es-1ge(494),
        nm-xd-24es-2st(495),
        nm-xd-48es-2ge(496),
        nm-16es-1ge-no-pwr(497),
        nm-xd-24es-2st-no-pwr(498),
        nm-xd-48es-2ge-no-pwr(499),
        nm-x-24es-1ge-no-pwr(500),
        c5750(506),
        cMWR1941DCA(507),
        cCRS18-linecard(513),
        cCRS1-fabric(514),
        cids4220(515),
        cids4230(516),
        ws-3020-hpq(518),
        ws-3030-del(519),
        cwlse-1133(520),
        spa-ipsec-2g-2(529),
        cips-virtual(543),
        c5720(544),
        c7201(548),
        ds-c9222i-k9(549),
        c5740(557),
        c7816-h(586),
        cuc500(591),
        c860-ap(592),
        c880-ap(593),
        c890-ap(594),
        c1900-ap(595)
        }
    ACCESS read-only
    STATUS deprecated
    DESCRIPTION
        "Chassis type."
    ::= { chassis 1 }

chassisVersion OBJECT-TYPE
    SYNTAX DisplayString
--    Rsyntax OCTET STRING
    ACCESS read-only
    STATUS deprecated
    DESCRIPTION
        "Chassis hardware revision level, or an empty
        string if unavailable."
    ::= { chassis 2 }

chassisId OBJECT-TYPE
    SYNTAX DisplayString
--    Rsyntax OCTET STRING
    ACCESS read-write
    STATUS deprecated
    DESCRIPTION
        "Unique ID string. Defaults to chassis serial
        number if available, otherwise empty. Can
        also be set with 'snmp-server chassis-id'."
    ::= { chassis 3 }

romVersion OBJECT-TYPE
    SYNTAX DisplayString
--    Rsyntax OCTET STRING
    ACCESS read-only
    STATUS deprecated
    DESCRIPTION
        "ROM monitor version."
    ::= { chassis 4 }

romSysVersion OBJECT-TYPE
    SYNTAX DisplayString
--    Rsyntax OCTET STRING
    ACCESS read-only
    STATUS deprecated
    DESCRIPTION
        "ROM system software version, or an empty
        string if unavailable."
    ::= { chassis 5 }

processorRam OBJECT-TYPE
    SYNTAX INTEGER
    ACCESS read-only
    STATUS deprecated
    DESCRIPTION
        "Bytes of RAM available to CPU."
    ::= { chassis 6 }

nvRAMSize OBJECT-TYPE
    SYNTAX INTEGER
    ACCESS read-only
    STATUS deprecated
    DESCRIPTION
        "Bytes of non-volatile configuration memory."
    ::= { chassis 7 }

nvRAMUsed OBJECT-TYPE
    SYNTAX INTEGER
    ACCESS read-only
    STATUS deprecated
    DESCRIPTION
        "Bytes of non-volatile configuration memory
        in use."
    ::= { chassis 8 }

configRegister OBJECT-TYPE
    SYNTAX INTEGER
    ACCESS read-only
    STATUS deprecated
    DESCRIPTION
        "Value of configuration register."
    ::= { chassis 9 }

configRegNext OBJECT-TYPE
    SYNTAX INTEGER
    ACCESS read-only
    STATUS deprecated
    DESCRIPTION
        "Value of configuration register at next
        reload."
    ::= { chassis 10 }

cardTable OBJECT-TYPE
    SYNTAX SEQUENCE OF CardTableEntry
    ACCESS not-accessible
    STATUS deprecated
    DESCRIPTION
        "Chassis card table."
    ::= { chassis 11 }

cardTableEntry OBJECT-TYPE
    SYNTAX CardTableEntry
    ACCESS not-accessible
    STATUS deprecated
    DESCRIPTION
        "Chassis card table."
    INDEX { cardIndex }
    ::= { cardTable 1 }

CardTableEntry ::= SEQUENCE {
    cardIndex INTEGER,
    cardType INTEGER,
    cardDescr DisplayString,
    cardSerial INTEGER,
    cardHwVersion DisplayString,
    cardSwVersion DisplayString,
    cardSlotNumber INTEGER,
    cardContainedByIndex INTEGER,
    cardOperStatus INTEGER,
    cardSlots INTEGER
    }

cardIndex OBJECT-TYPE
    SYNTAX INTEGER
    ACCESS read-only
    STATUS deprecated
    DESCRIPTION
        "Index into cardTable (not physical chassis
        slot number)."
    ::= { cardTableEntry 1 }

cardType OBJECT-TYPE
    SYNTAX INTEGER {
        unknown(1),
        csc1(2),
        csc2(3),
        csc3(4),
        csc4(5),
        rp(6),
        cpu-igs(7),
        cpu-2500(8),
        cpu-3000(9),
        cpu-3100(10),
        cpu-accessPro(11),
        cpu-4000(12),
        cpu-4000m(13),
        cpu-4500(14),
        rsp1(15),
        rsp2(16),
        cpu-4500m(17),
        cpu-1003(18),
        cpu-4700(19),
        csc-m(20),
        csc-mt(21),
        csc-mc(22),
        csc-mcplus(23),
        csc-envm(24),
        chassisInterface(25),
        cpu-4700S(26),
        cpu-7200-npe100(27),
        rsp7000(28),
        chassisInterface7000(29),
        rsp4(30),
        cpu-3600(31),
        cpu-as5200(32),
        c7200-io1fe(33),
        cpu-4700m(34),
        cpu-1600(35),
        c7200-io(36),
        cpu-1503(37),
        cpu-1502(38),
        cpu-as5300(39),
        csc-16(40),
        csc-p(41),
        csc-a(50),
        csc-e1(51),
        csc-e2(52),
        csc-y(53),
        csc-s(54),
        csc-t(55),
        csc-r(80),
        csc-r16(81),
        csc-r16m(82),
        csc-1r(83),
        csc-2r(84),
        sci4s(56),
        sci2s2t(57),
        sci4t(58),
        mci1t(59),
        mci2t(60),
        mci1s(61),
        mci1s1t(62),
        mci2s(63),
        mci1e(64),
        mci1e1t(65),
        mci1e2t(66),
        mci1e1s(67),
        mci1e1s1t(68),
        mci1e2s(69),
        mci2e(70),
        mci2e1t(71),
        mci2e2t(72),
        mci2e1s(73),
        mci2e1s1t(74),
        mci2e2s(75),
        csc-cctl1(100),
        csc-cctl2(101),
        csc-mec2(110),
        csc-mec4(111),
        csc-mec6(112),
        csc-fci(113),
        csc-fcit(114),
        csc-hsci(115),
        csc-ctr(116),
        cpu-7200-npe150(121),
        cpu-7200-npe200(122),
        cpu-wsx5302(123),
        gsr-rp(124),
        cpu-3810(126),
        cpu-2600(127),
        cpu-rpm(128),
        cpu-ubr904(129),
        cpu-6200-mpc(130),
        cpu-1700(131),
        cpu-7200-npe300(132),
        cpu-1400(133),
        cpu-800(134),
        cpu-psm-1gbps(135),
        cpu-7200-npe175(137),
        cpu-7200-npe225(138),
        cpu-1417(140),
        cpu-psm1-1oc12(141),
        cpu-optical-regenerator(142),
        cpu-ubr924(143),
        cpu-7120(144),
        cpu-7140(145),
        cpu-psm1-2t3e3(146),
        cpu-psm1-4oc3(147),
        cpu-ubr91x(149),
        sp(150),
        eip(151),
        fip(152),
        hip(153),
        sip(154),
        trip(155),
        fsip(156),
        aip(157),
        mip(158),
        ssp(159),
        cip(160),
        srs-fip(161),
        srs-trip(162),
        feip(163),
        vip(164),
        vip2(165),
        ssip(166),
        smip(167),
        posip(168),
        feip-tx(169),
        feip-fx(170),
        cbrt1(178),
        cbr120e1(179),
        cbr75e(180),
        vip2-50(181),
        feip2(182),
        acip(183),
        mc11(184),
        mc12a(185),
        io1fe-tx-isl(186),
        geip(187),
        vip4(188),
        mc14a(189),
        mc16a(190),
        mc11a(191),
        cip2(192),
        mc28(194),
        vip4-80(195),
        vip4-50(196),
        io-e-ge(197),
        io-2fe(198),
        npm-4000-fddi-sas(200),
        npm-4000-fddi-das(201),
        npm-4000-1e(202),
        npm-4000-1r(203),
        npm-4000-2s(204),
        npm-4000-2e1(205),
        npm-4000-2e(206),
        npm-4000-2r1(207),
        npm-4000-2r(208),
        npm-4000-4t(209),
        npm-4000-4b(210),
        npm-4000-8b(211),
        npm-4000-ct1(212),
        npm-4000-ce1(213),
        npm-4000-1a(214),
        npm-4000-6e-pci(215),
        npm-4000-1fe(217),
        npm-4000-1hssi(218),
        npm-4000-2e-pci(219),
        npm-4000-4gb(220),
        pa-1fe(230),
        pa-8e(231),
        pa-4e(232),
        pa-5e(233),
        pa-4t(234),
        pa-4r(235),
        pa-fddi(236),
        sa-encryption(237),
        pa-ah1t(238),
        pa-ah2t(239),
        pa-a4t(240),
        pa-a8t-v35(241),
        pa-1fe-tx-isl(242),
        pa-1fe-fx-isl(243),
        pa-1fe-tx-nisl(244),
        sa-compression(245),
        pa-atm-lite-1(246),
        pa-ct3(247),
        pa-oc3sm-mux-cbrt1(248),
        pa-oc3sm-mux-cbr120e1(249),
        pa-ds3-mux-cbrt1(254),
        pa-e3-mux-cbr120e1(255),
        pa-8b-st(257),
        pa-4b-u(258),
        pa-fddi-fd(259),
        pm-cpm-1e2w(260),
        pm-cpm-2e2w(261),
        pm-cpm-1e1r2w(262),
        pm-ct1-csu(263),
        pm-2ct1-csu(264),
        pm-ct1-dsx1(265),
        pm-2ct1-dsx1(266),
        pm-ce1-balanced(267),
        pm-2ce1-balanced(268),
        pm-ce1-unbalanced(269),
        pm-2ce1-unbalanced(270),
        pm-4b-u(271),
        pm-4b-st(272),
        pm-8b-u(273),
        pm-8b-st(274),
        pm-4as(275),
        pm-8as(276),
        pm-4e(277),
        pm-1e(278),
        pm-m4t(280),
        pm-16a(281),
        pm-32a(282),
        pm-c3600-1fe-tx(283),
        pm-c3600-compression(284),
        pm-dmodem(285),
        pm-8admodem(286),
        pm-16admodem(287),
        pm-c3600-1fe-fx(288),
        pm-1fe-2t1-csu(289),
        as5200-carrier(290),
        as5200-2ct1(291),
        as5200-2ce1(292),
        as5200-dtd-carrier(293),
        pm-as5xxx-12m(310),
        pm-as5xxx-12m-56k(311),
        pm-as5xxx-12m-v110(312),
        wm-c2500-5in1(330),
        wm-c2500-t1-csudsu(331),
        wm-c2500-sw56-2wire-csudsu(332),
        wm-c2500-sw56-4wire-csudsu(333),
        wm-c2500-bri(334),
        wm-c2500-bri-nt1(335),
        wic-serial-1t(360),
        wic-serial-2t(361),
        wic-csu-dsu-4(363),
        wic-s-t-3420(364),
        wic-s-t-2186(365),
        wic-u-3420(366),
        wic-u-2091(367),
        wic-u-2091-2081(368),
        wic-s-t-2186-leased(369),
        wic-t1-csudsu(370),
        wic-serial-2as(371),
        aim-compression(372),
        c3660-2fe-tx(373),
        pm-oc3mm(374),
        pm-oc3mm-vpd(375),
        pm-oc3smi-vpd(376),
        pm-oc3sml-vpd(377),
        pm-oc3sml(378),
        pm-oc3smi(379),
        pm-ima-4t1(380),
        pm-ima-8t1(381),
        pm-ima-4e1(382),
        pm-ima-8e1(383),
        nm-1fe-2w(384),
        nm-2fe-2w(385),
        nm-1fe-1r-2w(386),
        nm-2w(387),
        c36xx-1fe-tx(389),
        pa-jt2(400),
        pa-posdw(401),
        pa-4me1-bal(402),
        pa-2ce1-balanced(403),
        pa-2ct1(404),
        pa-1vg(405),
        pa-atmdx-ds3(406),
        pa-atmdx-e3(407),
        pa-atmdx-sml-oc3(408),
        pa-atmdx-smi-oc3(409),
        pa-atmdx-mm-oc3(410),
        pa-a8t-x21(414),
        pa-a8t-rs232(415),
        pa-4me1-unbal(416),
        pa-4r-fdx(417),
        pa-1e3(418),
        pa-2e3(419),
        pa-1t3(420),
        pa-2t3(421),
        pa-2ce1-unbalanced(422),
        pa-14e-switch(423),
        pa-1fe-fx-nisl(424),
        pa-esc-channel(425),
        pa-par-channel(426),
        pa-ge(427),
        pa-4ct1-csu(428),
        pa-8ct1-csu(429),
        c3800-vdm(430),
        c3800-vdm-dc-2t1e1(431),
        c3800-vdm-dc-1t1e1-enet(432),
        pa-2feisl-tx(433),
        pa-2feisl-fx(434),
        mc3810-dcm(435),
        mc3810-mfm-e1balanced-bri(436),
        mc3810-mfm-e1unbalanced-bri(437),
        mc3810-mfm-e1-unbalanced(438),
        mc3810-mfm-dsx1-bri(439),
        mc3810-mfm-dsx1-csu(440),
        mc3810-vcm(441),
        mc3810-avm(442),
        mc3810-avm-fxs(443),
        mc3810-avm-fxo(444),
        mc3810-avm-em(445),
        mc3810-vcm3(446),
        mc3810-bvm(447),
        mc3810-avm-fxo-uk(448),
        mc3810-avm-fxo-ger(449),
        mc3810-hcm2(450),
        mc3810-hcm6(451),
        mc3810-avm-fxo-pr3(452),
        mc3810-avm-fxo-pr2(453),
        mc3810-vdm(454),
        mc3810-apm-fxs-did(455),
        mc3810-bvm-nt-te(456),
        mc3810-hcm1(457),
        mc3810-hcm3(458),
        mc3810-hcm4(459),
        pm-dtd-6m(461),
        pm-dtd-12m(462),
        as5300-4ct1(480),
        as5300-4ce1(481),
        as5300-carrier(482),
        as5300-dtd-carrier(484),
        as5300-8ct1-4t(485),
        as5300-8ce1-4t(486),
        as5300-4ct1-4t(487),
        as5300-4ce1-4t(488),
        as5300-amazon2-carrier(489),
        vic-em(500),
        vic-fxo(501),
        vic-fxs(502),
        vpm-2v(503),
        vpm-4v(504),
        dsp-vfc30(505),
        dspm-c542(507),
        vic-2fxo-eu(508),
        vic-2fxo-m3(509),
        vic-2fxo-m4(510),
        vic-2fxo-m5(511),
        vic-2fxo-m6(512),
        vic-2fxo-m7(513),
        vic-2fxo-m8(514),
        vic-2st-2086(515),
        hdv(516),
        dspm-6c549(517),
        wvic-1dsu-t1(518),
        wvic-1dsu-e1(519),
        wvic-2dsu-t1(520),
        wvic-2dsu-e1(521),
        wvic-2dsu-t1-di(522),
        wvic-2dsu-e1-di(523),
        vic-2fxo-m2(525),
        hda-nm-4fxs(528),
        pos-qoc3-mm(530),
        pos-qoc3-sm(531),
        pos-oc12-mm(532),
        pos-oc12-sm(533),
        atm-oc12-mm(534),
        atm-oc12-sm(535),
        pos-oc48-mm-l(536),
        pos-oc48-sm-lr-fc(537),
        gsr-sfc(538),
        gsr-csc(539),
        gsr-csc4(540),
        gsr-csc8(541),
        gsr-sfc8(542),
        atm-qoc3-sm(543),
        atm-qoc3-mm(544),
        gsr-oc12chds3-mm(545),
        gsr-oc12chds3-sm(546),
        gsr-1ge(547),
        gsr-oc12chsts3-mm(548),
        gsr-oc12chsts3-sm(549),
        pos-oc48-sm-sr-fc(552),
        pos-qoc3-sm-l(553),
        pos-8oc3-mm(554),
        pos-8oc3-ir(555),
        pos-8oc3-lr(556),
        pos-16oc3-mm(557),
        pos-16oc3-ir(558),
        pos-16oc3-lr(559),
        pa-8ct1(560),
        pa-8ce1(561),
        pa-ce3(562),
        pa-4r-dtr(563),
        pa-possw-sm(564),
        pa-possw-mm(565),
        pa-possw-lr(566),
        pa-1t3-plus(567),
        pa-2t3-plus(568),
        pa-ima-t1(569),
        pa-ima-e1(570),
        pa-2ct1-csu(571),
        pa-2ce1(572),
        pa-2fe-tx(573),
        pa1-esc4-channel(575),
        pa2-oc3-pos-sw(576),
        pa-4dtr(577),
        pa-vm-hda-8fxs-did(578),
        pa1-oc3-pos-sw(579),
        pa-mcx-4te1-q(580),
        pm-1fe-1t1(600),
        pm-1fe-2t1(601),
        pm-1fe-1e1(602),
        pm-1fe-2e1(603),
        pm-1fe-1t1-csu(604),
        pm-atm25(605),
        pm-hssi(606),
        as5800-dsc(630),
        as5800-12t1(631),
        as5800-12e1(632),
        as5800-mica-hmm(633),
        as5800-t3(634),
        as5800-1fe-dsi(635),
        as5800-mica-dmm(636),
        as5800-vcc(637),
        as5800-dspm-6c549(638),
        as5800-dsp(639),
        slc-cap8(650),
        ntc-oc3si(651),
        ntc-oc3mm(652),
        ntc-stm1si(653),
        ntc-stm1mm(654),
        slc-dmt8(655),
        slc-dmt16(656),
        ntc-ds3(657),
        osm-1oc48-pos-ss(659),
        osm-1oc48-pos-sl(660),
        osm-1oc48-pos-si(661),
        osm-2oc12-pos-sl(664),
        osm-4oc12-pos-sl(665),
        osm-2oc12-pos-mm(666),
        osm-4oc12-pos-mm(667),
        osm-2oc12-pos-si(668),
        osm-4oc12-pos-si(669),
        osm-8oc3-pos-si(670),
        osm-16oc3-pos-si(671),
        osm-8oc3-pos-mm(672),
        osm-16oc3-pos-mm(673),
        osm-8oc3-pos-sl(674),
        osm-16oc3-pos-sl(675),
        osm-4ge-wan-gbic(676),
        osm-4ge-4oc12-chds3-sm-ir(680),
        osm-4ge-8oc12-chds3-sm-ir(681),
        osm-4ge-oc48-chds3-sm-sr(682),
        osm-4ge-2oc48-chds3-sm-sr(683),
        osm-4ge-oc48-chds3-sm-ir(684),
        osm-4ge-2oc48-chds3-sm-ir(685),
        osm-4ge-oc12-chds3-sm-ir(686),
        osm-4ge-2oc12-chds3-sm-ir(687),
        wsx-6582-2pa(689),
        wsx-6066-slbsk9(692),
        cat6k-wsf-6k-pfc3b(693),
        cat6k-wsf-6k-dfc3b(694),
        cat6k-wsf-6700-dfc3b(695),
        cat6k-wsf-6k-pfc3bxl(696),
        cat6k-wsf-6k-dfc3bxl(697),
        cat6k-wsf-6700-dfc3bxl(698),
        atmdx-rpm(750),
        pa-atm-oc12-mm(802),
        pa-atm-oc12-smi(803),
        pa-mct3(804),
        pa-mc2t3(805),
        pa-pos-oc12-mm(806),
        pa-pos-oc12-sm(807),
        srp-pa-oc12-mm(808),
        srp-pa-oc12-sm-ir(809),
        srp-pa-oc12-lr(810),
        pa-mcx-2te1(811),
        pa-mcx-4te1(812),
        pa-mcx-8te1(813),
        srp-pa-oc12-sm-xr(814),
        pa-mc-stm1-smi(817),
        pa-dual-wide-ge(819),
        pa-vxa-1t1e1-24(820),
        pa-vxa-1t1e1-30(821),
        pa-mc-8t1e1(822),
        pa-mcx-8te1-m(824),
        pa-a6-mm-oc3(825),
        pa-a6-smi-oc3(826),
        pa-a6-sml-oc3(827),
        pa-a6-ds3(828),
        pa-a6-e3(829),
        pa-mc-t3-ec(830),
        pa-mc-2t3-ec(831),
        pa-1t3e3-ec(832),
        pa-2t3e3-ec(833),
        ausm-8t1(850),
        ausm-8e1(851),
        cesm-8t1(852),
        cesm-8e1(853),
        frsm-8t1(854),
        frsm-8e1(855),
        frsm-4x21(856),
        frsm-2hssi(857),
        cesm-1t3(858),
        cesm-1e3(859),
        vism-8t1(860),
        vism-8e1(861),
        mgx-rpm(862),
        mgx-srm-3t3(863),
        vism-pr-8t1(899),
        wsx-2914(900),
        wsx-2922(901),
        wsx-2914-v(902),
        wsx-2922-v(903),
        wsx-2924-v(904),
        wsx-2951(905),
        wsx-2961(906),
        wsx-2971(907),
        wsx-2972(908),
        wsx-2931(909),
        lm-bnc-2t3(950),
        lm-bnc-2e3(951),
        lm-db15-4x21(952),
        lm-scsi2-2hssi(953),
        lm-rj48-8t1(954),
        lm-rj48-8t1-r(955),
        lm-rj48-8e1(956),
        lm-rj48-8e1-r(957),
        lm-smb-8e1(958),
        lm-smb-8e1-r(959),
        lm-psm-ui(960),
        lm-mmf-4oc3(961),
        lm-smfir-4oc3(962),
        lm-smflr-4oc3(963),
        lm-smfir-1oc12(964),
        lm-smflr-1oc12(965),
        lm-s3-ui(966),
        lm-1fe-tx(967),
        lm-1fe-fx(968),
        lm-1mmf-fddi(969),
        lm-1smf-fddi(970),
        lm-rj45-4e(971),
        lm-bnc-3t3(985),
        ubr-mc16s(1001),
        ubr-mc11(1002),
        ubr-mc11c(1003),
        ubr-mc12c(1004),
        ubr-mc14c(1005),
        ubr-mc16a(1006),
        ubr-mc16b(1007),
        ubr-mc16c(1008),
        ubr-mc16e(1009),
        ubr-mc28c(1010),
        ubr-mc26(1011),
        ubr-912c(1012),
        ubr-912s(1013),
        ubr-914r(1014),
        ubr-clk(1015),
        ubr-925(1016),
        ubr-mc26c(1017),
        ubr-mc28cf(1020),
        ubr-mc28c-bnc(1021),
        ubr-mc26cf(1022),
        ubr-mc26c-bnc(1023),
        ubr-905(1024),
        ubr-dlc24(1025),
        ubr-mc520s-f(1029),
        ubr-mc520s-bnc(1030),
        ubr-tccplus(1040),
        gsr-8fe-tx(1050),
        gsr-8fe-fx(1051),
        ssrp-oc48-sm-sr(1052),
        ssrp-oc48-sm-lr(1053),
        pos-qoc12-sm-lr(1054),
        pos-qoc12-mm-sr(1055),
        pos-oc48-sm-lr-sc(1056),
        pos-oc48-sm-sr-sc(1057),
        srp-oc12-sm-ir(1058),
        srp-oc12-sm-lr(1059),
        srp-oc12-mm(1060),
        pos-en-oc48-sr-sc(1061),
        pos-en-oc48-sr-fc(1062),
        pos-en-oc48-lr-sc(1063),
        pos-en-oc48-lr-fc(1064),
        pos-en-qoc12-sr(1065),
        pos-en-qoc12-ir(1066),
        copper-6ds3(1067),
        copper-12ds3(1068),
        gsr-sfc16(1073),
        gsr-csc16(1074),
        gsr-3ge(1075),
        gsr-alarm16(1076),
        gsr-bus-board16(1077),
        srp-oc12-sm-xr(1078),
        pos-en-qoc12-mm(1079),
        pos-en-qoc48-sm-sr-fc(1080),
        pos-en-qoc48-sm-sr-sc(1081),
        pos-en-qoc48-sm-lr-sc(1082),
        pos-en-qoc48-sm-lr-fc(1083),
        gsr-6ct3(1084),
        pos-en-oc192-sm-lr-fc(1085),
        pos-en-oc192-sm-lr-sc(1086),
        pos-en-oc192-sm-vsr-sc(1087),
        pos-en-oc192-sm-vsr-fc(1088),
        gsr-sfc16-oc192(1091),
        gsr-csc16-oc192(1092),
        gsr-qoc12-chstsds3-sm-ir-sc(1094),
        gsr-qoc12-chstsds3-mm-sr-sc(1095),
        gsr-oc48-chstsds3-mm-sr-sc(1096),
        gsr-oc48-chstsds3-sm-ir-sc(1097),
        gsr-oc48-chstsds3-sm-lr-sc(1098),
        gsr-16oc3-chstsds3-mm-sr-sc(1099),
        aim-lc-4e1-compression(1100),
        wic-csu-dsu-ft1(1105),
        pm-ds3(1106),
        pm-e3(1107),
        vic-2vp-fxs-did(1111),
        wic-serial-1t-12in1(1112),
        vic-2st-2086-nt-te(1113),
        nm-aic64(1114),
        mix3660-64(1115),
        wic-async-1am(1116),
        wic-async-2am(1117),
        hdv-4fxs(1120),
        c2610m(1121),
        c2611m(1122),
        wic-ethernet(1124),
        nm-1t3e3(1130),
        nm-1ct3e3(1131),
        nm-8ct1e1(1132),
        hda-em-4fxo(1133),
        c2610xm-1fe(1134),
        c2611xm-2fe(1135),
        c2620xm-1fe(1136),
        c2621xm-2fe(1137),
        c2650xm-1fe(1138),
        c2651xm-2fe(1139),
        nm-1ct1e1-pri(1147),
        nm-2ct1e1-pri(1148),
        io-2fe-tx-isl(1150),
        ism-ipsec-mppe(1151),
        vpn-accelerator(1152),
        vpn-accelerator-module2(1153),
        vpn-accelerator-AES(1154),
        vpn-am-2plus(1155),
        cre-rp(1180),
        cpu-as5400(1182),
        cpu-mc3810-v3(1185),
        cpu-7200-nse1(1186),
        cpu-as5850(1187),
        cpu-7200-npe400(1188),
        cpu-7150(1191),
        cpu-7401-nse(1193),
        cpu-gsr-prp1(1196),
        cpu-7200-npeg1(1203),
        cpu-c2691-2fe(1204),
        cpu-c3745-2fe(1205),
        cpu-c3725-2fe(1206),
        cpu-c3631-1fe(1207),
        cpu-6400-nsp(1209),
        cpu-6400-nrp(1210),
        cpu-6400-nrp2(1211),
        cpu-6400-nrp2-sv(1212),
        cpu-as5400-hpx(1217),
        cpu-vg224(1224),
        cpu-gsr-prp2(1228),
        cpu-c2801-2fe(1239),
        cpu-7201-npeg2(1243),
        acc-24fe-tx(1307),
        acc-24fe-fx-mm(1308),
        acc-24fe-fx-sm(1309),
        srp-oc48-sr(1310),
        srp-oc48-ir(1311),
        atm-4oc3(1313),
        acc-4ge8fe-tx(1323),
        acc-4ge8fe-fx-mm(1324),
        acc-4ge8fe-fx-sm(1325),
        ul-srp48-lr1(1326),
        ul-srp48-lr2(1327),
        c10720-mnt(1330),
        ul-pos-srp48-sm-sr(1332),
        ul-pos-srp48-sm-ir(1333),
        ul-pos-srp48-sm-lr1(1334),
        ul-pos-srp48-sm-lr2(1335),
        acc-24fe-tx-b(1336),
        acc-4ge8fe-tx-b(1337),
        ul-rpr-srp-48(1339),
        as5400-dfc-carrier(1350),
        as5400-dfc-np348(1351),
        as5400-dfc-np192(1352),
        dfc-8ce1(1450),
        dfc-8ct1(1451),
        dfc-ct3(1452),
        dfc-np108(1453),
        isa-ipsec-mppe(1454),
        wic-dslsar-20150(1455),
        wvic-2dsu-t1-dir(1462),
        wvic-2dsu-e1-dir(1463),
        vic-4vp-fxs-did(1464),
        vic-4fxo-us-m1(1465),
        vic-4fxo-m2-m3(1466),
        vic-4fxo-cama(1467),
        nm-se(1477),
        aim-se(1478),
        wic-se(1479),
        spa-ipsec-2g(1482),
        spa-2p-oc3-atm(1483),
        spa-4p-oc3-atm(1484),
        spa-1p-oc12-atm(1485),
        spa-1p-oc48-atm(1487),
        spa-2p-oc3-pos(1490),
        spa-4p-oc3-pos(1491),
        spa-1p-oc12-pos(1492),
        spa-4p-fe-7304(1495),
        spa-2p-ge-7304(1496),
        spa-1p-oc192-pos-rpr-xfp(1498),
        spa-1p-oc192-pos-rpr-sm-lr(1500),
        cat6k-wsx-sup-12ge(1502),
        cat6k-wsx-6408-gbic(1503),
        cat6k-wsx-6224-100fx-mt(1504),
        cat6k-wsx-6248-rj45(1505),
        cat6k-wsx-6248-tel(1506),
        cat6k-wsx-6302-msm(1507),
        cat6k-wsx-6024-mtrj(1509),
        cat6k-msfc2(1510),
        cat6k-wsx-6316-ge-tx(1511),
        cat6k-wsx-6416-gbic(1512),
        cat6k-wsx-6324-100fx(1513),
        cat6k-wsx-6348-rj45(1514),
        cat6k-wsx-6502-10ge(1515),
        cat6k-wsx-6066-slb-apc(1516),
        cat6k-wsx-6548-rj45(1518),
        cat6k-wsx-6248a-tel(1519),
        cat6k-wsx-sup2-2ge(1520),
        cat6k-wsc-6500-sfm(1521),
        cat6k-wsc-6500-sfm2(1522),
        cat6k-wsx-6816-gbic(1523),
        cat6k-wsx-6348-rj21(1528),
        cat6k-wsx-6516-gbic(1529),
        cat6k-wsx-sup1a-2ge(1530),
        cat6k-wsx-6548-rj21(1531),
        cat6k-wsx-6416-gemt(1532),
        cat6k-wsx-6380-nam(1533),
        cat6k-wsx-6248a-rj45(1534),
        cat6k-wsx-6408a-gbic(1535),
        cat6k-wsx-6381-ids(1536),
        cat6k-wsx-6524-mmmt(1537),
        cat6k-wsx-6516-getx(1538),
        cat6k-wsx-6501-10gex4(1539),
        cat6k-wsf-6kvpwr(1541),
        cat6k-ws-svc-nam1(1542),
        cat6k-ws-svc-nam2(1543),
        cat6k-ws-svc-fwm1(1544),
        cat6k-ws-svc-ssl1(1545),
        cat6k-wsx-6516a-gbic(1546),
        ipsec-vpnsm(1549),
        dspm-pvdm3(1556),
        dspm-pvdm1(1561),
        dspm-pvdm2(1562),
        dspm-pvdm4(1563),
        dspm-pvdm5(1564),
        hda-em-4dsp(1590),
        hda-em-10fxs(1591),
        wic-sh-dsl(1565),
        hdv-8fxs(1566),
        hdv-4dsp(1567),
        vic-4vp-fxs-4did(1573),
        em-4fxs-4fxo(1581),
        em-6fxo(1582),
        em-4bri-nt-te(1583),
        vic2-mft1-t1e1(1594),
        vic2-mft2-t1e1(1595),
        em2-hda-4fxo(1596),
        vic-1j1(1597),
        wic-1am-v2(1598),
        wic-2am-v2(1599),
        ituc-1p8(1611),
        atuc-1p8-dmt(1618),
        stuc-1p8(1619),
        atuc-1p8-dmt-itemp(1620),
        stuc-1p8-itemp(1621),
        cva122(1700),
        cva124(1701),
        cva122e(1702),
        cva124e(1703),
        as5850-epm-2ge(1750),
        as5850-ct3-216up(1751),
        as58xx-324up(1753),
        as5850-24e1(1754),
        gsr-16oc3-chstsds3-sm-ir-sc(1900),
        gsr-16oc3-chstsds3-sm-lr-sc(1901),
        gsr-2oc3-chds1(1905),
        ssrp-oc192-sm-lr(1906),
        ssrp-oc192-sm-ir(1907),
        ssrp-oc192-sm-sr(1908),
        ssrp-oc192-sm-vsr(1909),
        gsr-sfc10(1912),
        gsr-csc10(1913),
        gsr-alarm10(1914),
        gsr-bus-board10(1915),
        gsr-oc48-chstsds3-sm-sr-sc(1916),
        gsr-e48-pos-oc48-sm-sr-sc(1917),
        gsr-e48-pos-oc48-sm-lr-sc(1918),
        gsr-e48-pos-qoc12-sm-ir-sc(1919),
        gsr-e48-pos-16oc3-sm-ir-sc(1920),
        copper-6e3(1921),
        copper-12e3(1922),
        gsr-e48-pos-16oc3-sm-ir-lc(1926),
        gsr-16oc3-chstsds3-sm-ir-lc(1927),
        gsr-oc12-chds1-sm-ir-sc(1928),
        gsr-sfc6(1929),
        gsr-csc6(1930),
        gsr-alarm6(1931),
        pos-en-qoc48-vsr(1932),
        pos-en-qoc48-mm-sr-sc(1933),
        pos-en-qoc48-sm-ir-sc(1934),
        pos-en-qoc48-sm-ir-fc(1935),
        pos-en-qoc48-sm-vlr-sc(1936),
        pos-en-qoc48-sm-vlr-fc(1937),
        pos-en-qoc48-sm-elr-sc(1938),
        pos-en-qoc48-sm-elr-fc(1939),
        pos-en-oc192-vsr(1940),
        pos-en-oc192-sm-sr2-sc(1941),
        pos-en-oc192-sm-sr2-fc(1942),
        pos-en-oc192-sm-vlr-sc(1943),
        pos-en-oc192-sm-vlr-fc(1944),
        pos-en-oc192-sm-elr-sc(1945),
        pos-en-oc192-sm-elr-fc(1946),
        gsr-sfc12410(1947),
        gsr-csc12410(1948),
        iad2420-vm-8fxs(1950),
        iad2420-16fxs(1951),
        iad2420-vm-pwr(1952),
        iad2420-adsl(1953),
        iad2420-hcm1(1954),
        iad2420-hcm2(1955),
        iad2420-hcm3(1956),
        iad2420-hcm4(1957),
        iad2420-hcm5(1958),
        iad2420-hcm6(1959),
        iad2420-cpu(1960),
        iad2420-mfm-e1-unbalanced(1961),
        iad2420-mfm-e1-dsx1-csu(1962),
        iad2420-mfm-t1-dsx1-csu(1963),
        iad2420-8fxo(1964),
        iad2420-16fxs-off-premise(1967),
        gsr-atm-en-8oc3-mm(1968),
        gsr-oc48-msr(1969),
        iad2430-ob-8fxs(1983),
        iad2430-ob-16fxs(1984),
        iad2430-ob-24fxs(1985),
        iad2430-ob-t1e1(1986),
        mc3810-hcm5(2000),
        m10000base-lx4(2051),
        m10000base-ex4(2052),
        m10000base-lr(2053),
        m10000base-er(2054),
        m10000base-sx4(2055),
        c7401(2100),
        io-c7401-ge(2101),
        c7411-npeg1(2128),
        io-c7411-ge(2129),
        vip6-80(2132),
        c7300-cc-pa(2138),
        c7200-vsa(2155),
        gsr-1p10ge(2200),
        gsr-e48-pos-oc48-sm-ir-sc(2201),
        gsr-e-oc192-sm-lr-sc(2203),
        gsr-e-oc192-sm-vsr-sc(2204),
        gsr-e-oc192-sm-vsr-fc(2205),
        gsr-e-oc192-sm-sr-fc(2206),
        gsr-e-oc192-sm-sr-sc(2207),
        gsr-e-oc192-sm-lr-fc(2208),
        gsr-e-qoc48-sm-lr-fc(2209),
        gsr-e-qoc48-sm-lr-sc(2210),
        gsr-e-qoc48-sm-vsr-sc(2211),
        gsr-e-qoc48-sm-vsr-fc(2212),
        gsr-e-qoc48-sm-sr-fc(2213),
        gsr-e-qoc48-sm-sr-sc(2214),
        gsr-e-qoc48-vsr(2215),
        gsr-e-qoc48-sm-sr2-sc(2216),
        gsr-e-qoc48-sm-sr2-fc(2217),
        gsr-e-qoc48-mm-sr-sc(2218),
        gsr-e-qoc48-sm-ir-sc(2219),
        gsr-e-qoc48-sm-ir-fc(2220),
        gsr-e-qoc48-sm-vlr-sc(2221),
        gsr-e-qoc48-sm-vlr-fc(2222),
        gsr-e-qoc48-sm-elr-sc(2223),
        gsr-e-qoc48-sm-elr-fc(2224),
        gsr-e-oc192-vsr(2225),
        gsr-e-oc192-sm-sr2-sc(2226),
        gsr-e-oc192-sm-sr2-fc(2227),
        gsr-e-oc192-mm-sr-sc(2228),
        gsr-e-oc192-sm-ir-sc(2229),
        gsr-e-oc192-sm-ir-fc(2230),
        gsr-e-oc192-sm-vlr-sc(2231),
        gsr-e-oc192-sm-vlr-fc(2232),
        gsr-e-oc192-sm-elr-sc(2233),
        gsr-e-oc192-sm-elr-fc(2234),
        ssrp-2oc48-srp-sm-sr-lc(2236),
        ssrp-2oc48-srp-sm-ir-lc(2237),
        ssrp-2oc48-srp-sm-lr-lc(2238),
        ssrp-2oc48-pos-sm-sr-lc(2239),
        ssrp-2oc48-pos-sm-ir-lc(2240),
        ssrp-2oc48-pos-sm-lr-lc(2241),
        gsr-gefe(2244),
        gsr-pa-3ge(2246),
        gsr-pa-24fe(2247),
        gsr-e48-atm-4oc12-sm-ir-sc(2248),
        gsr-e48-atm-4oc12-mm-sr-sc(2249),
        ssrp-e48-2oc12-sm-ir(3008),
        ssrp-e48-2oc12-sm-xr(3009),
        ssrp-e48-1oc12-sm-ir(3010),
        ssrp-e48-1oc12-sm-xr(3011),
        gsr-sip-600(3016),
        gsr-6ds3e3-smb(3028),
        gsr-6ds3e3ct3-smb(3029),
        gsr-2oc3-chds1ds3e3-sm-ir-sc(3030),
        gsr-sip-601(3044),
        gsr-sip-501(3045),
        gsr-sip-401(3046),
        gsr-ssrp2-oc48-lc(3047),
        vism-pr-8e1(3050),
        vxsm-4oc3(3051),
        mgx-srm-4oc3(3052),
        hd-dsp(4015),
        nm-8am-v2(4020),
        nm-16am-v2(4021),
        cpu-c2811-2fe(4023),
        cpu-c2821-2ge(4024),
        cpu-c2851-2ge(4025),
        hwic-serial4t(4026),
        hwic-serial4as(4027),
        hwic-serial8as(4028),
        hwic-serial8a(4029),
        hwic-serial16a(4030),
        nme-16es-1ge-no-pwr(4042),
        nme-x-24es-1ge-no-pwr(4043),
        nme-xd-48es-2ge-no-pwr(4044),
        nme-xd-24es-2st-no-pwr(4045),
        cat6k-ws-sup720(4050),
        cat6k-ws-sup720-base(4051),
        cat6k-wsx-6802-10ge(4052),
        cat6k-wsx-6832-sfp(4053),
        cat6k-wsx-6748-getx(4054),
        cat6k-wsx-6704-10ge(4055),
        cat6k-wsx-6748-sfp(4056),
        cat6k-wsx-6724-sfp(4057),
        cat6k-wsf-6k-pfc(4058),
        cat6k-wsf-6k-pfc2(4059),
        cat6k-wsf-6k-dfc(4060),
        cat6k-wsf-6k-pfc3a(4061),
        cat6k-wsf-6k-dfc3a(4062),
        cat6k-wsx-6148-ge-tx(4063),
        cat6k-wsx-6148-rj21(4064),
        cat6k-wsx-6148-rj45(4065),
        cat6k-wsx-6548-getx(4066),
        cat6k-wsf-6700-dfc3a(4067),
        cat6k-wsx-6324-100fx-sm(4068),
        cat6k-ws-svc-idsm2(4069),
        cat6k-ws-svc-idsupg(4070),
        cat6k-wsx-6148x2-rj45(4071),
        cat6k-wsf-6k-fe48x2-af(4072),
        cat6k-wsf-6k-fe48-af(4073),
        cat6k-wsf-6k-ge48-af(4074),
        cat6k-wsf-6k-vpwr-ge(4075),
        cat6k-wsf-6700-cfc(4076),
        cat6k-ws-svc-wlan1-k9(4077),
        cat6k-ws-svc-aon1(4078),
        cat6k-ws-sup32-ge(4079),
        cat6k-ws-sup32-10ge(4080),
        cat6k-msfc2a(4081),
        cat6k-ws-6340-sup(4082),
        cat6k-ws-6340-lca(4083),
        cat6k-ws-6340-lcb(4084),
        cat6k-wsx-6196-rj21(4091),
        cat6k-wsx-6148-fe-sfp(4092),
        cat6k-wsx-6148a-getx(4093),
        cat6k-wsx-6148a-rj45(4094),
        cat6k-wsg-6483(4095),
        cat6k-wsg-6485(4096),
        cat6k-wsg-6488(4097),
        cat6k-wsg-6489(4098),
        cat6k-ws-svc-webvpnk9(4099),
        oc3-sfp(4100),
        oc12-sfp(4101),
        osm-2oc48-pos-ss(4102),
        osm-2oc48-pos-si(4103),
        osm-2oc48-pos-sl(4104),
        osm-1oc48-srp-ss(4105),
        osm-1oc48-srp-si(4106),
        osm-1oc48-srp-sl(4107),
        pwr-ac-465w(4113),
        oc192-xfp-smsr1(4128),
        oc192-xfp-smir2(4129),
        oc192-xfp-smlr2(4130),
        cable50cm-sfp(4131),
        pwr-ac-125w(4132),
        pwr-ac-60w(4133),
        pwr-dsCAD-6000W(4138),
        pwr-cat3750-ac210w12v(4139),
        pwr-cat3750-ac375w48v(4140),
        pwr-crs116-power-shelf-ac-delta(4141),
        pwr-crs116-power-shelf-ac-wye(4142),
        pwr-crs116-power-shelf-dc(4143),
        pwr-crs116-ac-rectifier(4144),
        pwr-crs116-dc-pem(4145),
        pwr-ds-cac-3000w(4146),
        pwr-6000-dc(4147),
        dwdm-3033-sfp(4148),
        dwdm-3112-sfp(4149),
        dwdm-3190-sfp(4150),
        spa-1p-oc192-pos-rpr-vsr(4201),
        spa-8p-ct1e1(4202),
        spa-2p-ct3(4203),
        spa-4p-ct3(4204),
        spa-10p-ge(4211),
        spa-1p-10ge-xfp(4212),
        spa-5p-ge(4213),
        spa-2p-t3e3-serial(4217),
        spa-4p-t3e3-serial(4218),
        spa-2p-ge(4219),
        hwic-dot11-bg(4221),
        spa-1p-choc3-stm1(4222),
        aim-vpn-bp(4223),
        aim-vpn-ep(4224),
        nm-vpn-mp(4225),
        aim-vpn-hp(4226),
        aim-vpn-bp2(4227),
        aim-vpn-ep2(4228),
        aim-vpn-hp2(4229),
        aim-vpn-bp2-plus(4230),
        aim-vpn-ep2-plus(4231),
        aim-vpn-hp2-plus(4232),
        hwic-adsl-bri-pots(4233),
        hwic-adsl-bri-isdn(4234),
        hwic-adsl-isdn(4235),
        hwic-adsl-pots(4236),
        spa-2p-oc48-pos-rpr-hh(4237),
        mds-ds-x9530-sf2-k9(4238),
        mds-ds-x9112(4239),
        mds-ds-x9124(4240),
        mds-ds-x9148(4241),
        mds-ds-x9704(4242),
        nm-cue-ec(4244),
        mds-ds-13-slt-fab1(4245),
        mds-ds-c9513-cl(4246),
        dfc-dl108(4247),
        dfc-dl60(4248),
        c356024-ts(4252),
        c356048-ts(4253),
        ce-scsi-2636(4357),
        ce-ide-2636(4358),
        wic-t1-csudsu-v2(4450),
        spa-8xfe-tx(4451),
        crs14-oc192-ir-plim(4460),
        spa-8x-ge(4461),
        wic-1-shdsl-v3(4465),
        usb-flash(4466),
        usb-token(4467),
        usb-hub(4468),
        usb-device(4470),
        nm-cips(4477),
        hwic-1fe(4478),
        hwic-2fe(4479),
        mds-ds-x9222i-k9-sup(4494),
        mds-ds-x9304-18k9(4497),
        cat6k-wsx-6708a-10ge(4500),
        cat6k-wsx-6708-10ge(4501),
        cat6k-wsf-6700-dfc3c(4503),
        cat6k-wsf-6700-dfc3cxl(4504),
        hwic-4shdsl(4551),
        hwic-2shdsl(4552),
        nm-rvpn-sterra(4553),
        nm-rvpn(4554),
        mn-spcl-srvc-eng(4555),
        nm-intgrtd-srvc-eng2(4556),
        dwdm-3268-sfp(4600),
        dwdm-3425-sfp(4601),
        dwdm-3504-sfp(4602),
        dwdm-3582-sfp(4603),
        dwdm-3661-sfp(4604),
        dwdm-3819-sfp(4605),
        dwdm-3898-sfp(4606),
        dwdm-3977-sfp(4607),
        dwdm-4056-sfp(4608),
        dwdm-4214-sfp(4609),
        dwdm-4294-sfp(4610),
        dwdm-4373-sfp(4611),
        dwdm-4453-sfp(4612),
        dwdm-4612-sfp(4613),
        dwdm-4692-sfp(4614),
        dwdm-4772-sfp(4615),
        dwdm-4851-sfp(4616),
        dwdm-5012-sfp(4617),
        dwdm-5092-sfp(4618),
        dwdm-5172-sfp(4619),
        dwdm-5252-sfp(4620),
        dwdm-5413-sfp(4621),
        dwdm-5494-sfp(4622),
        dwdm-5575-sfp(4623),
        dwdm-5655-sfp(4624),
        dwdm-5817-sfp(4625),
        dwdm-5898-sfp(4626),
        dwdm-5979-sfp(4627),
        dwdm-6061-sfp(4628)
        }
    ACCESS read-only
    STATUS deprecated
    DESCRIPTION
        "Functional type of this card."
    ::= { cardTableEntry 2 }

cardDescr OBJECT-TYPE
    SYNTAX DisplayString
--    Rsyntax OCTET STRING
    ACCESS read-only
    STATUS deprecated
    DESCRIPTION
        "Text description of this card."
    ::= { cardTableEntry 3 }

cardSerial OBJECT-TYPE
    SYNTAX INTEGER
    ACCESS read-only
    STATUS deprecated
    DESCRIPTION
        "The serial number of this card, or zero if
        unavailable."
    ::= { cardTableEntry 4 }

cardHwVersion OBJECT-TYPE
    SYNTAX DisplayString
--    Rsyntax OCTET STRING
    ACCESS read-only
    STATUS deprecated
    DESCRIPTION
        "Hardware revision level of this card, or an
        empty string if unavailable."
    ::= { cardTableEntry 5 }

cardSwVersion OBJECT-TYPE
    SYNTAX DisplayString
--    Rsyntax OCTET STRING
    ACCESS read-only
    STATUS deprecated
    DESCRIPTION
        "Version of the firmware or microcode
        installed on this card, or an empty string if
        unavailable."
    ::= { cardTableEntry 6 }

cardSlotNumber OBJECT-TYPE
    SYNTAX INTEGER
    ACCESS read-only
    STATUS deprecated
    DESCRIPTION
        "Slot number relative to the containing card or 
        chassis, or -1 if neither applicable nor 
        determinable."
    ::= { cardTableEntry 7 }

cardContainedByIndex OBJECT-TYPE
    SYNTAX INTEGER
    ACCESS read-only
    STATUS deprecated
    DESCRIPTION
        "cardIndex of the parent card which
        directly contains this card, or 0 if
        contained by the chassis, or -1 if not
        applicable nor determinable."
    ::= { cardTableEntry 8 }

cardOperStatus OBJECT-TYPE
    SYNTAX INTEGER {
        not-specified(1),
        up(2),
        down(3),
        standby(4)
        }
    ACCESS read-only
    STATUS deprecated
    DESCRIPTION
        "The operational status of the card.
        cardOperStatus is up when a card is
        recognized by the device and is enabled for
        operation. cardOperStatus is down if the
        card is not recognized by the device, or if
        it is not enabled for operation.
        cardOperStatus is standby if the card is
        enabled and acting as a standby slave"
    ::= { cardTableEntry 9 }

cardSlots OBJECT-TYPE
    SYNTAX INTEGER
    ACCESS read-only
    STATUS deprecated
    DESCRIPTION
        "Number of slots on this card, or 0 if no
        slots or not applicable, or -1 if not 
        determinable."
    ::= { cardTableEntry 10 }

chassisSlots OBJECT-TYPE
    SYNTAX INTEGER
    ACCESS read-only
    STATUS deprecated
    DESCRIPTION
        "Number of slots in this chassis, or -1 of
        neither applicable nor determinable."
    ::= { chassis 12 }

cardIfIndexTable OBJECT-TYPE
    SYNTAX SEQUENCE OF CardIfIndexEntry
    ACCESS not-accessible
    STATUS deprecated
    DESCRIPTION
        "Chassis card table."
    ::= { chassis 13 }

cardIfIndexEntry OBJECT-TYPE
    SYNTAX CardIfIndexEntry
    ACCESS not-accessible
    STATUS deprecated
    DESCRIPTION
        "Chassis card table."
    INDEX { cardIfIndex }
    ::= { cardIfIndexTable 1 }

CardIfIndexEntry ::= SEQUENCE {
    cardIfIndex INTEGER,
    cardIfSlotNumber INTEGER,
    cardIfPortNumber INTEGER,
    cardIfCardIndex INTEGER,
    cardIfConnectorTypeEnabled INTEGER
    }

cardIfIndex OBJECT-TYPE
    SYNTAX INTEGER
    ACCESS read-only
    STATUS deprecated
    DESCRIPTION
        "matches RFC1213 ifTable IfIndex"
    ::= { cardIfIndexEntry 1 }

cardIfSlotNumber OBJECT-TYPE
    SYNTAX INTEGER
    ACCESS read-only
    STATUS deprecated
    DESCRIPTION
        "Chassis slot number, or -1 if neither
        applicable nor determinable."
    ::= { cardIfIndexEntry 2 }

cardIfPortNumber OBJECT-TYPE
    SYNTAX INTEGER
    ACCESS read-only
    STATUS deprecated
    DESCRIPTION
        "Chassis port number, unique per port on a 
         given card if available. If cardIfPortNumber is not
         applicable to the card, then the object instance
         won't be populated"
    ::= { cardIfIndexEntry 3 }

cardIfCardIndex OBJECT-TYPE
    SYNTAX INTEGER
    ACCESS read-only
    STATUS deprecated
    DESCRIPTION
        "cardIndex of the card in the Chassis 
         cardTable which contains this interface, or -1 if
         not applicable."
    ::= { cardIfIndexEntry 4 }

cardIfConnectorTypeEnabled OBJECT-TYPE
    SYNTAX INTEGER {
        not-specified(1),
        none(2),
        rj-45(3),
        db-40(4),
        db-15(5),
        auto-select(6),
        gbic-sx(7),
        gbic-lx(8),
        gbic-lh(9),
        gbic-cx(10),
        gbic-zx(11),
        missing(12),
        mmf-st(13),
        mmf-sc(14),
        rj-11(15),
        rj-48s(16),
        rj-48c(17),
        db-60(18),
        gbic-stack(19),
        gbic-1000baset(20)
        }
    ACCESS read-only
    STATUS deprecated
    DESCRIPTION
        "Interface connector type currently
        enabled. Value will be 1 if not known or not
        used, or 2 if none of this ports' interface
        connectors are enabled."
    ::= { cardIfIndexEntry 5 }

chassisPartner OBJECT-TYPE
    SYNTAX INTEGER {
        cisco(1),
        synoptics(2),
        chipcom(3),
        cabletron(4),
        dec(5),
        ncr(6),
        usrobotics(7),
        alcatel(8),
        nec(9),
        dsc(10),
        microcom(11),
        oki(12),
        ubn(13),
        hp(14),
        samsung(15),
        mitsubishi(16)
        }
    ACCESS read-only
    STATUS deprecated
    DESCRIPTION
        "Used to determine if this is a partner 
         variant of a product."
    ::= { chassis 14 }

sysUpTimeAtLastChassisChange OBJECT-TYPE
    SYNTAX TimeTicks
    ACCESS read-only
    STATUS deprecated
    DESCRIPTION
        "Time in seconds/100 from the last cold
        start to the last change in the chassis'
        configuration. This value will be updated
        whenever the chassis experiences a change
        in the count, type, or slot position of
        a card in cardTable."
    ::= { chassis 15 }


END
