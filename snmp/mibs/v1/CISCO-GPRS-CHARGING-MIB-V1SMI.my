-- MIB file created 22-Nov-2006 10:31:44, by
--   SMICng version 2.2.11-beta(PRO)(Solaris), January 20, 2001. Enterprise key cisco.com

CISCO-GPRS-CHARGING-MIB DEFINITIONS ::= BEGIN

-- From file: "CISCO-GPRS-CHARGING-MIB.my"
-- Compile options "4 7 F H N O W 03 06 0B 0G 0N 0T"

IMPORTS
    TruthValue, RowStatus, TestAndIncr, StorageType
            FROM SNMPv2-TC-v1
    SnmpAdminString
            FROM SNMP-FRAMEWORK-MIB
    InetAddressType, InetAddress
            FROM INET-ADDRESS-MIB
    CiscoAlarmSeverity
            FROM CISCO-TC
    ciscoMgmt
            FROM CISCO-SMI
    Counter, Gauge
            FROM RFC1155-SMI
    OBJECT-TYPE
            FROM RFC-1212
    TRAP-TYPE
            FROM RFC-1215;

ciscoGprsChargingMIB OBJECT IDENTIFIER ::= { ciscoMgmt 192 }
-- MODULE-IDENTITY
--  LastUpdated
--    200608180000Z
--  OrgName
--    Cisco Systems, Inc.
--  ContactInfo
--           Cisco Systems 
--            Customer Service 
--    
--    Postal: 170 W Tasman Drive 
--            San Jose, CA  95134 
--            USA 
--    
--       Tel: +1 800 553-NETS 
--    
--    E-mail: cs-gprs@cisco.com
--  Descr
--    This MIB module manages the charging related 
--    function on the GGSN node of a GPRS system. 
--    
--    The following diagram illustrates a simplified GPRS 
--    logical architecture with the interface name 
--    denotations: 
--    
--    +==+     +===+     +====+        +====+        +===+ 
--    |MS|=====|BSS|=====|SGSN|===Gn===|GGSN|===Gi===|PDN| 
--    +==+     +===+     +====+        +====+        +===+ 
--                            \          / 
--                             Ga       Ga 
--                              \ +==+ / 
--                                |CG|
--                                +==+ 
--    
--    Charging information in GPRS is collected for each MS 
--    by SGSNs and GGSNs that are serving that MS. The GGSN 
--    collects charging information for each MS based on  
--    both external data network usage and the GPRS network  
--    resources.  
--    
--    Acronyms and terms: 
--    
--     BSS    Base Station System
--     CCA    Credit Control Answer
--     CDR    Call Detail Record 
--     CID    Charging Identification 
--     CG     Charging Gateway 
--     CGF    Charging Gateway Functionality  
--     DCCA   Diameter Credit Control Application
--     ETSI   European Telecommunications Standards 
--            Institute 
--     Ga     Name of the interface between SGSN/GGSN and CG 
--     Gi     Name of the interface between GGSN and PDN 
--     Gn     Name of the interface between GGSN and SGSN 
--     G-CDR  Gateway GPRS Support Node-Call Detail Record   
--     GGSN   Gateway GPRS Support Node 
--     GPRS   General Packet Radio Service 
--     GSM    Global System for Mobile communication 
--     GTP    GPRS Tunneling Protocol 
--     GTP'   GTP enchanced for charging  
--     IE     Information Element
--     MS     Mobile Station 
--     PDN    Packet Data Network
--     PDP    Packet Data Protocol 
--     SGSN   Serving GPRS support Node 
--     TOS    Type of Service. 
--     PSD    Persistance Storage Device.
--     PTC    Packet Transfer Command.
--  RevDate
--    200608180000Z
--  RevDescr
--    - Deprecated following objects
--         cgprsCgProfileMapNum, 
--         cgprsCgProfileContentPostValTime.
--    
--     - Added following objects
--         cgprsCgProfileMapNumber,
--         cgprsCgProfileContentPostValidityTime.
--    
--     - Deprecated following groups and compliance
--         cgprsCgMIBConfigGroupR60, 
--         cgprsCgMIBConfigGroupRev3,
--         cgprsCgComplianceRev5.
--     
--     - Added following group, compliance
--         cgprsCgMIBConfigGroupRev4,
--         cgprsCgMIBExtConfigGroup.
--         cgprsCgComplianceRev6.
--  RevDate
--    200604041900Z
--  RevDescr
--    Added following objects in cgprsCgProfileTable:
--        cgprsCgProfileContentPostQosChange,
--        cgprsCgProfileContentPostSgsnChange,
--        cgprsCgProfileContentPostRatChange,
--        cgprsCgProfileContentPostPlmnChange,
--        cgprsCgProfileStorageType
--    
--    Changed the DEFVAL of cgprsCgCdrOptionDynamicAddr,
--    cgprsCgCdrOptionNip,
--    cgprsCgCdrOptionPdpType and 
--    cgprsCgCdrOptionPdpAddress from 'false' to 'true'.
--    
--    Added following objects in ciscoGprsChargingConfig:
--       cgprsCgServiceRecordIncludeRat, 
--       cgprsCgServiceRecordIncludePlmn
--    
--    Changed the DEFVAL of the following objects:
--       cgprsCgProfileCategory,
--       cgprsCgContainerTimeLimit.
--  RevDate
--    200509161800Z
--  RevDescr
--    Added cgprsCgCdrOptionServiceRecord,
--    cgprsCgPartialCdrGenEnableAll,
--    cgprsCgCdrOptionApn,
--    cgprsCgCdrOptionVirtualApn,
--    cgprsCgCdrOptionApnSelMode,
--    cgprsCgCdrOptionDynamicAddr,
--    cgprsCgCdrOptionNip,
--    cgprsCgCdrOptionPdpAddress,
--    cgprsCgCdrOptionPdpType,
--    cgprsCgCdrOptionSerMsisdn,
--    cgprsCgCdrOptionSgsnPlmn
--    cgprsCgCdrOptionCamelCharInfo,
--    cgprsCgCdrOptionImeisv,
--    cgprsCgCdrOptionMsTimeZone,
--    cgprsCgCdrOptionRatType,
--    cgprsCgCdrOptionUserLocInfo to 
--    ciscoGprsChargingConfig.
--    
--    Added cgprsCgProfileCdrSuppressPrepaid,
--    cgprsCgProfileContentDccaProfile,
--    cgprsCgProfileContentPostTime,
--    cgprsCgProfileContentPostValTime,
--    cgprsCgProfileContentPostVolume,
--    cgprsCgProfileContentRulebaseId to
--    cgprsCgProfileTable.
--    
--    Added cgprsCgTotalServiceRecords to
--    ciscoGprsChargingStats.
--  RevDate
--    200407260200Z
--  RevDescr
--    Modified the description for cgprsCgProfileDurLimit
--    and cgprsCgProfileVolumeLimit.
--  RevDate
--    200403220300Z
--  RevDescr
--    Added cgprsCgContainerTimeLimit, cgprsCgProfileTable,
--     cgprsCgProfileMapTable, cgprsCgServiceMode,
--     cgprsCgChargingCharReject, cgprsCgPartialCdrGenEnable 
--     cgprsCgSwitchOverPriority, cgprsCgCharSelectionMode,
--     cgprsCgReconnect, cgprsCgPtcEnable,
--     cgprsCgPtcPossiblyDupEnable to 
--     ciscoGprsChargingConfig.
--     Updated cgprsCgRelease. 
--     Added cgprsCgGatewaySwitchoverNotif, 
--     cgprsCgInServiceModeNotif, cgprsCgMaitenanceModeNotif 
--     to ciscoGprsCharNotifs.
--     Added cgprsCgActiveChgGatewayAddrType,
--     cgprsCgActiveChgGatewayAddress,
--     cgprsCgOldChgGatewayAddress to
--     ciscoGprsChargingStatus.
--     Obsoleted cgprsCgCdrNonPrimaryEnable.
--  RevDate
--    200211111700Z
--  RevDescr
--    Added cgprsCgRelease, cgprsCgGtpShortHeaderEnable and
--     cgprsCgTransFormNumRespEnable to 
--     ciscoGprsChargingConfig.
--     Deprecated cgprsCgCdrNonPrimaryEnable.
--  RevDate
--    200206051000Z
--  RevDescr
--    Added cgprsCgCdrSgsnChangeLimit to 
--     ciscoGprsChargingConfig. 
--     Deprecated cgprsCgSgsnChangeLimit.
--     Added cgprsCgAlarmHistLatestIndex to 
--     ciscoGprsChargingAlarms.
--     Updated DEFVAL of cgprsCgConditionLimit.
--     Added cgprsCgAlarmChargingDisabled, 
--     cgprsCgAlarmChargingEnabled to CgprsCgAlarmType.
--     Enums for cgprsCgClearCdrPartialCdr have been
--     modified to comply with the standards.
--  RevDate
--    200112041200Z
--  RevDescr
--    
--    Added the objects cgprsCgPartialCdrTrigger,
--    cgprsCgSgsnChangeLimit, cgprsCgTotalCdrOpened
--    cgprsCgTotalContainer.  
--  RevDate
--    200109181600Z
--  RevDescr
--    
--    Added an object cgprsCgChargeForRoamersOnly.
--    
--    Added cgprsCgMIBNotifGroup to MODULE-COMPLIANCE.
--    
--    Added range for cgprsCgCdrAggreLimit,
--    cgprsCgPathRequest.
--    
--    Changed the syntax of cgprsCgTransInterval from
--    TimeInterval to Unsigned32. Moreover changed its
--    default value from 10500 to 105.
--    
--    Changed the syntax of cgprsCgServerSwitchTimeout from
--    TimeInterval to Unsigned32. Moreover changed its
--    default value from 6000 to 60.
--    
--    Changed the range of cgprsCgN3BufferSize from <100 -
--    1480> to <300 - 1460> and its default value has been
--    changed from 1480 to 1460.
--    
--    Changed the syntax of cgprsCgAlarmHistSeverity from
--    INTEGER to CiscoAlarmSeverity.
--    
--    Changed the syntax from IpAddress to InetAddress for
--    the objects cgprsCgGatewayAddr and
--    cgprsCgAlarmHistAddress.
--    
--    Changed the description for cgprsCgGatewayRowStatus.
--    
--    Replaced the object:
--    - cgprsCgGatewayType with cgprsCgGatewayIndex.
--    - cgprsCgGatewayOperState with cgprsCgOperStatus.
--    - cgprsCgGatewayAdminState with cgprsCgLinkState.
--    
--    
--    Removed the object cgprsCgAlarmHistStatus and the
--    textual convention CgprsCgAlarmStatus.
--  RevDate
--    200009210000Z
--  RevDescr
--     Initial version of this MIB module.

ciscoGprsChargingMIBObjects OBJECT IDENTIFIER ::= { ciscoGprsChargingMIB 1 }
ciscoGprsChargingConfig OBJECT IDENTIFIER ::= { ciscoGprsChargingMIBObjects 1 }
ciscoGprsChargingOthers OBJECT IDENTIFIER ::= { ciscoGprsChargingMIBObjects 2 }
ciscoGprsChargingStats OBJECT IDENTIFIER ::= { ciscoGprsChargingMIBObjects 3 }
ciscoGprsChargingAlarms OBJECT IDENTIFIER ::= { ciscoGprsChargingMIBObjects 4 }
ciscoGprsChargingStatus OBJECT IDENTIFIER ::= { ciscoGprsChargingMIBObjects 5 }
ciscoGprsCharNotifPrefix OBJECT IDENTIFIER ::= { ciscoGprsChargingMIB 2 }
ciscoGprsCharNotifs OBJECT IDENTIFIER ::= { ciscoGprsCharNotifPrefix 0 }
ciscoGprsCharMIBConformances OBJECT IDENTIFIER ::= { ciscoGprsChargingMIB 3 }
cgprsCgMIBCompliances OBJECT IDENTIFIER ::= { ciscoGprsCharMIBConformances 1 }
cgprsCgMIBGroups OBJECT IDENTIFIER ::= { ciscoGprsCharMIBConformances 2 }

CgprsCgAlarmType ::= INTEGER {
        cgprsCgAlarmCgDown(1),
        cgprsCgAlarmCgUp(2),
        cgprsCgAlarmTransFailure(3),
        cgprsCgAlarmTransSuccess(4),
        cgprsCgAlarmCapacityFull(5),
        cgprsCgAlarmCapacityFree(6),
        cgprsCgAlarmEchoFailure(7),
        cgprsCgAlarmEchoRestored(8),
        cgprsCgAlarmCdrDiscard(9),
        cgprsCgAlarmCdrBuffered(10),
        cgprsCgAlarmChargingDisabled(11),
        cgprsCgAlarmChargingEnabled(12)
        }
-- TEXTUAL-CONVENTION
--  Status
--    mandatory
--  Descr
--    Identifies the possible types of GPRS 
--     charging gateway and charging related alarm.
--    
--    cgprsCgAlarmCgDown 
--      - CG is down.  
--    cgprsCgAlarmCgUp 
--      - CG is up.
--    cgprsCgAlarmTransFailure 
--      - The GGSN has repeatedly 
--        failed to receive responses 
--        for Data Record Transfer Request Messages from CG.
--    cgprsCgAlarmTransSuccess
--      - The GGSN has successfully sent Data Record Transfer
--        Request Message to CG after the failure.
--    cgprsCgAlarmCapacityFull 
--      - The GGSN is out of memory and has failed to buffer 
--        a G-CDR internally.  
--    cgprsCgAlarmCapacityFree
--      - The GGSN is able to buffer G-CDR after the failure to 
--        buffer G-CDRs.
--    cgprsCgAlarmEchoFailure 
--      - The GGSN has repeatedly failed to receive the Echo
--        Response Messages from the CG for the Echo Request 
--        message.
--    cgprsCgAlarmEchoRestored
--      - The GGSN has got the Echo Response from the CG after 
--        the cgprsCgAlarmEchoFailure has been detected.
--    cgprsCgAlarmCdrDiscard 
--      - The G-CDRs are discarded. 
--    cgprsCgAlarmCdrDiscardRestored
--      - This is to indicate that GGSN has started buffering G-CDRs
--        after cgprsCgAlarmCdrDiscard has occured. 
--    cgprsCgAlarmChargingDisabled
--      - Indicates that charging transactions on the GGSN 
--        are disabled.
--    cgprsCgAlarmChargingEnabled
--      - Indicates that charging transactions on the GGSN 
--        are enabled.

cgprsCgEnable OBJECT-TYPE
    SYNTAX TruthValue
--    Rsyntax INTEGER {
--        true(1),
--        false(2)
--        }
    ACCESS read-write
    STATUS mandatory
    DESCRIPTION
        "This object is used to enable/disable the charging 
        transaction feature on the GGSN. When the object is 
        set to 'true', charging processing is enabled on the GGSN."
    DEFVAL { true }
    ::= { ciscoGprsChargingConfig 1 }

cgprsCgCdrLocalSeqNumEnable OBJECT-TYPE
    SYNTAX TruthValue
--    Rsyntax INTEGER {
--        true(1),
--        false(2)
--        }
    ACCESS read-write
    STATUS mandatory
    DESCRIPTION
        "This object is used to enable/disable the feature of using 
        the local record sequence number field in G-CDRs on the GGSN. 
        When the object is set to 'true', the G-CDRs contain the local 
        record sequence number in the CDR."
    DEFVAL { false }
    ::= { ciscoGprsChargingConfig 2 }

cgprsCgCdrNodeIdEnable OBJECT-TYPE
    SYNTAX TruthValue
--    Rsyntax INTEGER {
--        true(1),
--        false(2)
--        }
    ACCESS read-write
    STATUS mandatory
    DESCRIPTION
        "This object is used to enable/disable the feature of using 
        the NodeID field in G-CDRs on the GGSN.  When the object is 
        set to 'true', the G-CDRs include the NodeID field."
    DEFVAL { false }
    ::= { ciscoGprsChargingConfig 3 }

cgprsCgFlowControlEcho OBJECT-TYPE
    SYNTAX TruthValue
--    Rsyntax INTEGER {
--        true(1),
--        false(2)
--        }
    ACCESS read-write
    STATUS mandatory
    DESCRIPTION
        "This object is used to enable/disable flow control 
        between the GGSN and CG. 
        When the object is set to 'true', the GGSN enables private 
        extension information element in the echo request. This is 
        used for maintaining flow control on packets transmitted 
        to the CG."
    DEFVAL { false }
    ::= { ciscoGprsChargingConfig 4 }

cgprsCgCdrPktsStatEnable OBJECT-TYPE
    SYNTAX TruthValue
--    Rsyntax INTEGER {
--        true(1),
--        false(2)
--        }
    ACCESS read-write
    STATUS mandatory
    DESCRIPTION
        "This object is used to enable/disable G-CDR packet statistics 
        collection. When the object is set to 'true', the G-CDR is 
        enabled to collect the packet statistics from  
        cgprsGtpChargingPktsUplink and cgprsGtpChargingPktsDownlink 
        object."
    DEFVAL { false }
    ::= { ciscoGprsChargingConfig 5 }

cgprsCgCdrNonPrimaryEnable OBJECT-TYPE
    SYNTAX TruthValue
--    Rsyntax INTEGER {
--        true(1),
--        false(2)
--        }
    ACCESS read-write
    STATUS obsolete
    DESCRIPTION
        "This object controls the generation of non-primary 
        partial CDRs on GGSN as follows:
         'true(1)' - the generation of non-primary partial CDRs 
                     is enabled.
         'false(2)'- the generation of non-primary partial CDRs is 
                     disabled and all partial CDRs have the same 
                     content of primary partial CDRs."
    DEFVAL { true }
    ::= { ciscoGprsChargingConfig 6 }

cgprsCgCdrAggreLimit OBJECT-TYPE
    SYNTAX Gauge(1..255)
--  Units
--    CDRs
    ACCESS read-write
    STATUS mandatory
    DESCRIPTION
        "The Maximum number of G-CDRs that can be aggregated in a  
        charging data transfer message to a CG."
    DEFVAL { 255 }
    ::= { ciscoGprsChargingConfig 7 }

cgprsCgTransInterval OBJECT-TYPE
    SYNTAX Gauge(1..4294967295)
--  Units
--    seconds
    ACCESS read-write
    STATUS mandatory
    DESCRIPTION
        "Specifies the time interval between transfers of 
        GPRS charging data for a PDP context (user session)
        between the GGSN and the charging gateway."
    DEFVAL { 105 }
    ::= { ciscoGprsChargingConfig 8 }

cgprsCgPktsQSize OBJECT-TYPE
    SYNTAX Gauge(1..512)
--  Units
--    PDUs
    ACCESS read-write
    STATUS mandatory
    DESCRIPTION
        "The maximum size of the GGSN's queue of outstanding charging 
        data transfer requests."
    DEFVAL { 128 }
    ::= { ciscoGprsChargingConfig 9 }

cgprsCgPathRequest OBJECT-TYPE
    SYNTAX Gauge(0..10)
--  Units
--    minutes
    ACCESS read-write
    STATUS mandatory
    DESCRIPTION
        "The time interval between two TCP connection establishment  
        retry attempts if the TCP connection can't be established 
        for the communication with CG."
    DEFVAL { 0 }
    ::= { ciscoGprsChargingConfig 10 }

cgprsCgContainerVolThresh OBJECT-TYPE
    SYNTAX Gauge(1..4294967295)
--  Units
--    bytes
    ACCESS read-write
    STATUS mandatory
    DESCRIPTION
        "The traffic volume threshold that triggers addition of a 
        container and closing the G-CDR."
    DEFVAL { 1048576 }
    ::= { ciscoGprsChargingConfig 11 }

cgprsCgMapDataTos OBJECT-TYPE
    SYNTAX Gauge(0..5)
    ACCESS read-write
    STATUS mandatory
    DESCRIPTION
        "Specifies a IP Type of Service (TOS) mapping for GPRS  
        charging data packets transmitted by the GGSN. A higher 
        TOS mapping value indicates a higher service priority.
        The values '6' and '7' are not used in the mapping."
    DEFVAL { 3 }
    ::= { ciscoGprsChargingConfig 12 }

cgprsCgPathProtocol OBJECT-TYPE
    SYNTAX INTEGER {
        udp(1),
        tcp(2)
        }
    ACCESS read-write
    STATUS mandatory
    DESCRIPTION
        "Specifies the transport protocol used by the GGSN to transmit 
        and receive charging data to and from a CG. 
          udp -  use UDP for charging data transfers.   
          tcp -  use TCP for charging data transfers."
    DEFVAL { udp }
    ::= { ciscoGprsChargingConfig 13 }

cgprsCgServerSwitchTimeout OBJECT-TYPE
    SYNTAX Gauge(0..300)
--  Units
--    seconds
    ACCESS read-write
    STATUS mandatory
    DESCRIPTION
        "A timeout value that determines when the GGSN attempts to  
        switch over to an alternate CG after a destination CG cannot 
        be located or becomes unusable. Setting value 0 disables this
        feature."
    DEFVAL { 60 }
    ::= { ciscoGprsChargingConfig 14 }

cgprsCgConditionLimit OBJECT-TYPE
    SYNTAX Gauge(1..100)
    ACCESS read-write
    STATUS mandatory
    DESCRIPTION
        "The maximum number of charging condition changes to  
        trigger closure of a G-CDR partial record. When the 
        maximum number is reached, the G-CDR is closed and  
         a new partial G-CDR is opened."
    DEFVAL { 5 }
    ::= { ciscoGprsChargingConfig 15 }

cgprsCgGtpPrimePort OBJECT-TYPE
    SYNTAX Gauge(1024..10000)
    ACCESS read-write
    STATUS mandatory
    DESCRIPTION
        "The destination port for transferring G-CDR between GGSN 
        and CG. The port number is used for both UDP and TCP."
    DEFVAL { 3386 }
    ::= { ciscoGprsChargingConfig 16 }

cgprsCgN3BufferSize OBJECT-TYPE
    SYNTAX Gauge(300..1460)
--  Units
--    bytes
    ACCESS read-write
    STATUS mandatory
    DESCRIPTION
        "The transmit buffer size for sending GTP' PDU."
    DEFVAL { 1460 }
    ::= { ciscoGprsChargingConfig 17 }

cgprsCgChargeForRoamersOnly OBJECT-TYPE
    SYNTAX TruthValue
--    Rsyntax INTEGER {
--        true(1),
--        false(2)
--        }
    ACCESS read-write
    STATUS mandatory
    DESCRIPTION
        "This object is used to indicate to the GGSN that it needs to
        generate CDRs only for roamers. When the object is set
        to 'false' GGSN will generate CDRs for non-roamers also.
        This option only affects new PDP contexts while the ones 
        that have already been created are not affected."
    DEFVAL { false }
    ::= { ciscoGprsChargingConfig 18 }

cgprsCgTariffTimeMaxEntries OBJECT-TYPE
    SYNTAX Gauge(1..32)
    ACCESS read-only
    STATUS mandatory
    DESCRIPTION
        "Indicates the upper limit on the number of entries that the
        cgprsCgTariffTimeTable  may contain."
    DEFVAL { 32 }
    ::= { ciscoGprsChargingConfig 19 }

cgprsCgTariffTimeNextIndex OBJECT-TYPE
    SYNTAX TestAndIncr
--    Rsyntax INTEGER(0..2147483647)
    ACCESS read-write
    STATUS mandatory
    DESCRIPTION
        "This object contains an appropriate value to
        be used for cgprsCgTariffTimeIndex when creating 
        entries in the cgprsCgTariffTimeTable. The value 0 
        indicates that no new rows can be created. Otherwise, 
        it is recommended that values are assigned contiguously,
        starting from 1.
        Algorithm for Tariff Time creation by a Manager:
            done = false
            while done == false
            begin
             index = GET (cgprsCgTariffTimeNextIndex.0)
             if ( index == 0 ) break;
              SET (cgprsCgTariffTimeNextIndex.0=index) &&
               SET(cgprsCgTariffTimeRowStatus.index=createAndGo)
              if (set failed)
                done = false
              else
                done = true
            end."
    ::= { ciscoGprsChargingConfig 20 }

cgprsCgTariffTimeTable OBJECT-TYPE
    SYNTAX SEQUENCE OF CgprsCgTariffTimeEntry
    ACCESS not-accessible
    STATUS mandatory
    DESCRIPTION
        "The tariff time table. The tariff time table contains all 
        currently configured tariff times on the GGSN"
    ::= { ciscoGprsChargingConfig 21 }

cgprsCgTariffTimeEntry OBJECT-TYPE
    SYNTAX CgprsCgTariffTimeEntry
    ACCESS not-accessible
    STATUS mandatory
    DESCRIPTION
        "A description of a tariff time entry. An entry is created
        whenever a tariff time is configured. When the GPRS tariffs 
        time is reached, a container will be attached to the G-CDR 
        for the user. A new entry cannot be created in this table 
        when the table is full."
    INDEX { cgprsCgTariffTimeIndex }
    ::= { cgprsCgTariffTimeTable 1 }

CgprsCgTariffTimeEntry ::= SEQUENCE {
    cgprsCgTariffTimeIndex Gauge,
    cgprsCgTariffTimeRowStatus RowStatus,
    cgprsCgTariffTimeHour Gauge,
    cgprsCgTariffTimeMin Gauge,
    cgprsCgTariffTimeSec Gauge
    }

cgprsCgTariffTimeIndex OBJECT-TYPE
    SYNTAX Gauge
    ACCESS not-accessible
    STATUS mandatory
    DESCRIPTION
        "An arbitrary non-zero integer value uniquely identifying 
        each charging tariff time. "
    ::= { cgprsCgTariffTimeEntry 1 }

cgprsCgTariffTimeRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table. 
        The objects in this table can't be modified if the value 
        of this object is 'active'.RowStatus options 'notInService' 
        and 'createAndWait' are not supported."
    ::= { cgprsCgTariffTimeEntry 2 }

cgprsCgTariffTimeHour OBJECT-TYPE
    SYNTAX Gauge(0..23)
--  Units
--    hours
    ACCESS read-write
    STATUS mandatory
    DESCRIPTION
        "Specifies the hours part of GPRS tariffs time."
    ::= { cgprsCgTariffTimeEntry 3 }

cgprsCgTariffTimeMin OBJECT-TYPE
    SYNTAX Gauge(0..59)
--  Units
--    minutes
    ACCESS read-write
    STATUS mandatory
    DESCRIPTION
        "Specifies the minutes part of GPRS tariffs time."
    ::= { cgprsCgTariffTimeEntry 4 }

cgprsCgTariffTimeSec OBJECT-TYPE
    SYNTAX Gauge(0..59)
--  Units
--    seconds
    ACCESS read-write
    STATUS mandatory
    DESCRIPTION
        "Specifies the seconds part of GPRS tariffs time."
    ::= { cgprsCgTariffTimeEntry 5 }

cgprsCgGatewayTable OBJECT-TYPE
    SYNTAX SEQUENCE OF CgprsCgGatewayEntry
    ACCESS not-accessible
    STATUS mandatory
    DESCRIPTION
        "Charging gateway table.  
        The table contains a list of charging gateways.
        A charging gateway contains databases to store the 
        collected G-CDRs for billing purposes."
    ::= { ciscoGprsChargingConfig 22 }

cgprsCgGatewayEntry OBJECT-TYPE
    SYNTAX CgprsCgGatewayEntry
    ACCESS not-accessible
    STATUS mandatory
    DESCRIPTION
        "A conceptual row in the cgprsCgGatewayTable."
    INDEX { cgprsCgGatewayIndex }
    ::= { cgprsCgGatewayTable 1 }

CgprsCgGatewayEntry ::= SEQUENCE {
    cgprsCgGatewayIndex INTEGER,
    cgprsCgGatewayAddrType InetAddressType,
    cgprsCgGatewayAddr InetAddress,
    cgprsCgGatewayRowStatus RowStatus,
    cgprsCgOperStatus INTEGER,
    cgprsCgLinkState INTEGER
    }

cgprsCgGatewayIndex OBJECT-TYPE
    SYNTAX INTEGER(1..3)
    ACCESS not-accessible
    STATUS mandatory
    DESCRIPTION
        "An unique identifier for the CG."
    ::= { cgprsCgGatewayEntry 1 }

cgprsCgGatewayAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object indicates the type of Internet address
        given in cgprsCgGatewayAddr."
    ::= { cgprsCgGatewayEntry 2 }

cgprsCgGatewayAddr OBJECT-TYPE
    SYNTAX InetAddress
--    Rsyntax OCTET STRING(SIZE(0..255))
    ACCESS read-write
    STATUS mandatory
    DESCRIPTION
        "The IP address that is used to uniquely identify the CG."
    ::= { cgprsCgGatewayEntry 3 }

cgprsCgGatewayRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        cgprsCgGatewayAddrType and cgprsCgGatewayAddr are the
        mandatory objects in a create request.
        
        To delete a row, set this object to 'destroy'."
    ::= { cgprsCgGatewayEntry 4 }

cgprsCgOperStatus OBJECT-TYPE
    SYNTAX INTEGER {
        undefined(1),
        active(2),
        standby(3)
        }
    ACCESS read-only
    STATUS mandatory
    DESCRIPTION
        "This object is used to indicate whether the configured CG 
        is active(2) or standby(3).The object will return undefined(1) 
        when its not used either as active(2) or standby(3)."
    DEFVAL { undefined }
    ::= { cgprsCgGatewayEntry 5 }

cgprsCgLinkState OBJECT-TYPE
    SYNTAX INTEGER {
        on(1),
        off(2),
        pending(3)
        }
    ACCESS read-only
    STATUS mandatory
    DESCRIPTION
        "This object is used to indicate the reachability of the CG.
        If the CG is reachable then this object is set to 'on'. When
        the CG is not reachable but the GGSN tries to establish a 
        connection then the object will be set to 'pending' state. 
        When the CG is not reachable then the value returned for this 
        object will be 'off'."
    ::= { cgprsCgGatewayEntry 6 }

cgprsCgClearCdrPartialCdr OBJECT-TYPE
    SYNTAX INTEGER {
        closeCdr(1),
        canCloseCdr(2),
        cannotCloseCdr(3),
        closingCdr(4)
        }
    ACCESS read-write
    STATUS mandatory
    DESCRIPTION
        "This object is used to close all existing CDRs, transfer them 
        to the CG and open new partial CDRs for any existing PDP 
        contexts.
           closeCdr - close all existing CDRs.
           canCloseCdr - CDRs can be closed. This object can be set
           to 'closeCdr' only when it is in 'canCloseCdr' state.
           cannotCloseCdr - CDRs cannot be closed.  
           closingCdr - CDRs are being closed."
    ::= { ciscoGprsChargingConfig 23 }

cgprsCgSgsnChangeLimit OBJECT-TYPE
    SYNTAX Gauge(0..15)
    ACCESS read-write
    STATUS deprecated
    DESCRIPTION
        "This object denotes the maximum number of SGSN changes that 
        will trigger the closure of G-CDR or partial record. When the 
        maximum number is reached, the record is closed and a new 
        partial record is opened.  When the value is zero, then for 
        every SGSN change, the G-CDR or partial record is closed.
        This object is deprecated by cgprsCgCdrSgsnChangeLimit."
    DEFVAL { 15 }
    ::= { ciscoGprsChargingConfig 24 }

cgprsCgCdrSgsnChangeLimit OBJECT-TYPE
    SYNTAX INTEGER(-1..15)
    ACCESS read-write
    STATUS mandatory
    DESCRIPTION
        "This object denotes the maximum number of SGSN changes that
        will trigger the closure of G-CDR or partial record. When the
        maximum number is reached, the record is closed and a new
        partial record is opened.  When the value is zero, then for
        every SGSN change, the G-CDR or partial record is closed.
        If the value of object is set to '-1', then the number of 
        SGSN changes is not associated with the closure of G-CDR
        or creation/closure of partial record."
    DEFVAL { -1 }
    ::= { ciscoGprsChargingConfig 25 }

cgprsCgRelease OBJECT-TYPE
    SYNTAX INTEGER {
        release98(1),
        release99(2),
        release4(3),
        release5(4)
        }
    ACCESS read-write
    STATUS mandatory
    DESCRIPTION
        "This object specifies the release specific parameters that
        needs to be used when communicating with the CG. for eg:
        Qos Profile Info, Charging Characteristics field, etc.,
        
        This object also defines the charging release to enable the
        CRs implemented in GGSN version 5.0 (GGSN version is
        defined in cGgsnVersion in CISCO-GGSN-MIB, which is out of
        scope of this MIB).
        
        'release98' - No behavior change in GGSN 5.0.
        'release99' - From the baseline support of R99 that we 
                      already have in GGSN4.0, add support of 32.015 
                      CR 032 with the latest (Data Record Format 
                      Version) of 32.015 v3.10.0.
        'release4' or 'release5' - From the baseline support of R99 
                      in GGSN 5.0, add 32.215 CR 002 and Charging 
                      Characteristics Selection Mode."
    REFERENCE
        "3G TS 32.015 V3.2.0, Release99 Charging.
         GSM 12.15 V7.4.0, Release98 GPRS Charging.
         3GPP TS 32.215."
    DEFVAL { release99 }
    ::= { ciscoGprsChargingConfig 26 }

cgprsCgGtpShortHeaderEnable OBJECT-TYPE
    SYNTAX TruthValue
--    Rsyntax INTEGER {
--        true(1),
--        false(2)
--        }
    ACCESS read-write
    STATUS mandatory
    DESCRIPTION
        "This object enables the GGSN to use the 6-byte GTP short 
        header for charging transactions. This object cannot be
        toggled when there are pending CDR's."
    DEFVAL { false }
    ::= { ciscoGprsChargingConfig 27 }

cgprsCgTransFormNumRespEnable OBJECT-TYPE
    SYNTAX TruthValue
--    Rsyntax INTEGER {
--        true(1),
--        false(2)
--        }
    ACCESS read-write
    STATUS mandatory
    DESCRIPTION
        "When this object is set to 'true', the data record transfer
        response IE uses the one octet format which contains the 
        number of records responded. When set to 'false', it uses the
        2-octet format and it contains the length of this IE. This
        object cannot be toggled when there are active MS sessions on
        the GGSN."
    DEFVAL { false }
    ::= { ciscoGprsChargingConfig 28 }

cgprsCgContainerTimeLimit OBJECT-TYPE
    SYNTAX Gauge(0|5..4294967295)
--  Units
--    seconds
    ACCESS read-write
    STATUS mandatory
    DESCRIPTION
        "A G-CDR is used to collect charging information related
        to the packet data information for a GPRS mobile in the
        GGSN.The List of Traffic Data Volumes attribute of the
        G-CDR consists of a set of containers, that can be closed
        on certain trigers conditions like,
        
        - Data volume limit
        - Time duration limit
        - Maximum number of change condition limit
        
        This object when set to some non-zero time value, enables 
        the G-CDR updation when the time limit is reached."
    REFERENCE
        "3GPP; Technical Specification Group Services and System
        Aspects; Telecommunication Management; Charging and billing;
        GSM call and event data for the Packet Switched (PS) domain
        (Release 1999); 3GPP TS 32.015"
    DEFVAL { 0 }
    ::= { ciscoGprsChargingConfig 29 }

cgprsCgProfileTable OBJECT-TYPE
    SYNTAX SEQUENCE OF CgprsCgProfileEntry
    ACCESS not-accessible
    STATUS mandatory
    DESCRIPTION
        "Charging characteristics is a parameter introduced in 
        Release 99.Charging Characteristics allows the operator 
        to apply different charging methods on a per PDP basis.
        
        Charging Characteristics is a 2-octet parameter:
        
        The first 4 bits of the first octet, the 'P' bits, is called 
        the charging profile index. It specifies up to 16 different 
        charging profiles. 
        
        The remaining bits, the 'B' bits, can be used to further 
        characterize the Charging behavior. 
        
        Charging characteristics can be received from the SGSN as an 
        IE in the create PDP request message or from locally defined 
        defaults. There can be local default at the access-point or 
        GGSN levels. At either level, there may be also different 
        defaults for home, roaming, visiting subscribers, etc.
        
        This table allows to create a charging profile and define
        all the characteristics for that profile. This profile
        will be mapped to some APN."
    ::= { ciscoGprsChargingConfig 30 }

cgprsCgProfileEntry OBJECT-TYPE
    SYNTAX CgprsCgProfileEntry
    ACCESS not-accessible
    STATUS mandatory
    DESCRIPTION
        "An entry is created for each charging profile, with the
        characteristics of the charging being configured, it has
        some default characteristics when not configured."
    INDEX { cgprsCgProfileNum }
    ::= { cgprsCgProfileTable 1 }

CgprsCgProfileEntry ::= SEQUENCE {
    cgprsCgProfileNum Gauge,
    cgprsCgProfileRowStatus RowStatus,
    cgprsCgProfileDesc SnmpAdminString,
    cgprsCgProfileCategory INTEGER,
    cgprsCgProfileCdrSuppress TruthValue,
    cgprsCgProfileVolumeLimit Gauge,
    cgprsCgProfileVolumeLimitReset TruthValue,
    cgprsCgProfileDurLimit Gauge,
    cgprsCgProfileDurLimitReset TruthValue,
    cgprsCgProfileTariffTime TruthValue,
    cgprsCgProfileSgsnChange INTEGER,
    cgprsCgProfileCdrSuppressPrepaid TruthValue,
    cgprsCgProfileContentDccaProfile SnmpAdminString,
    cgprsCgProfileContentPostTime Gauge,
    cgprsCgProfileContentPostValTime Gauge,
    cgprsCgProfileContentPostVolume Gauge,
    cgprsCgProfileContentRulebaseId SnmpAdminString,
    cgprsCgProfileContentPostQosChange TruthValue,
    cgprsCgProfileContentPostSgsnChange TruthValue,
    cgprsCgProfileContentPostRatChange TruthValue,
    cgprsCgProfileContentPostPlmnChange TruthValue,
    cgprsCgProfileStorageType StorageType,
    cgprsCgProfileContentPostValidityTime Gauge
    }

cgprsCgProfileNum OBJECT-TYPE
    SYNTAX Gauge(0..65535)
    ACCESS not-accessible
    STATUS mandatory
    DESCRIPTION
        "This object is the charging profile index. This object
        represents the 'P' bits in charging characteristics."
    ::= { cgprsCgProfileEntry 1 }

cgprsCgProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        
        To delete a row, set this object to 'destroy'.
        
        Only these two values 'createAndGo' and 'destroy'
        will be accepted.  The table objects can be
        modified, when the RowStatus (cgprsCgProfileRowStatus) is 
        active."
    ::= { cgprsCgProfileEntry 2 }

cgprsCgProfileDesc OBJECT-TYPE
    SYNTAX SnmpAdminString(SIZE(1..99))
--    Rsyntax OCTET STRING(SIZE(1..99))
    ACCESS read-write
    STATUS mandatory
    DESCRIPTION
        "This object is used to describe this profile."
    ::= { cgprsCgProfileEntry 3 }

cgprsCgProfileCategory OBJECT-TYPE
    SYNTAX INTEGER {
        --?? enum value of zero may cause problems
        hotRate(0),
        flat(1),
        prepaid(2),
        normal(3)
        }
    ACCESS read-write
    STATUS mandatory
    DESCRIPTION
        "This object defines the charging profile category.
        
        hotRate(0) - Charging by hot billing.
        flat(1)    - Flat rate charging.
        prepaid(2) - Prepaid charging.
        normal(3)  - Normal charging."
    REFERENCE
        "3GPP TS 32.215 V5.5.0 (2003-12), section 5.6"
    DEFVAL { normal }
    ::= { cgprsCgProfileEntry 4 }

cgprsCgProfileCdrSuppress OBJECT-TYPE
    SYNTAX TruthValue
--    Rsyntax INTEGER {
--        true(1),
--        false(2)
--        }
    ACCESS read-write
    STATUS mandatory
    DESCRIPTION
        "This object specifies the generation of CDRs.
        If set to 'true', there won't be any CDRs generated.
        If set to 'false', the CDRs will be generated."
    DEFVAL { false }
    ::= { cgprsCgProfileEntry 5 }

cgprsCgProfileVolumeLimit OBJECT-TYPE
    SYNTAX Gauge(1..4294967295)
--  Units
--    bytes
    ACCESS read-write
    STATUS mandatory
    DESCRIPTION
        "This object specifies the volume limit at which the
        CDR updation has to take place."
    DEFVAL { 1048576 }
    ::= { cgprsCgProfileEntry 6 }

cgprsCgProfileVolumeLimitReset OBJECT-TYPE
    SYNTAX TruthValue
--    Rsyntax INTEGER {
--        true(1),
--        false(2)
--        }
    ACCESS read-write
    STATUS mandatory
    DESCRIPTION
        "This object is used to reset the volume limit timer 
        specified in cgprsCgProfileVolumeLimit when another
        trigger occurs. 
        
        If set to 'true' the volume limit timer will be reset when
        another trigger such as duration limit occurs.
        
        If set to 'false', the volume timer will continue until 
        it reaches the value set in cgprsCgProfileVolumeLimit."
    DEFVAL { false }
    ::= { cgprsCgProfileEntry 7 }

cgprsCgProfileDurLimit OBJECT-TYPE
    SYNTAX Gauge(0|5..4294967295)
--  Units
--    minutes
    ACCESS read-write
    STATUS mandatory
    DESCRIPTION
        "This object specifies the time limit in which the
        CDR updation has to take place.
        
        The value '0' means no duration limit."
    DEFVAL { 0 }
    ::= { cgprsCgProfileEntry 8 }

cgprsCgProfileDurLimitReset OBJECT-TYPE
    SYNTAX TruthValue
--    Rsyntax INTEGER {
--        true(1),
--        false(2)
--        }
    ACCESS read-write
    STATUS mandatory
    DESCRIPTION
        "This object is used to reset the duration limit timer
        specified in cgprsCgProfileDurLimit when another
        trigger occurs.
        
        If set to 'true' the duration limit timer will be reset when
        another trigger such as volume limit occurs.
        
        If set to 'false', the duration timer will continue until 
        it reaches the value set in cgprsCgProfileDurLimit."
    DEFVAL { false }
    ::= { cgprsCgProfileEntry 9 }

cgprsCgProfileTariffTime OBJECT-TYPE
    SYNTAX TruthValue
--    Rsyntax INTEGER {
--        true(1),
--        false(2)
--        }
    ACCESS read-write
    STATUS mandatory
    DESCRIPTION
        "This object enables the tariff time for this profile."
    DEFVAL { false }
    ::= { cgprsCgProfileEntry 10 }

cgprsCgProfileSgsnChange OBJECT-TYPE
    SYNTAX INTEGER(-1..15)
    ACCESS read-write
    STATUS mandatory
    DESCRIPTION
        "This object denotes the maximum number of SGSN changes that
         will trigger the closure of G-CDR or partial record. When the
         maximum number is reached, the record is closed and a new
         partial record is opened.  When the value is zero, then for
         every SGSN change, the G-CDR or partial record is closed.
        
         The value '-1' indicates no sgsn change limit."
    DEFVAL { -1 }
    ::= { cgprsCgProfileEntry 11 }

cgprsCgProfileCdrSuppressPrepaid OBJECT-TYPE
    SYNTAX TruthValue
--    Rsyntax INTEGER {
--        true(1),
--        false(2)
--        }
    ACCESS read-write
    STATUS mandatory
    DESCRIPTION
        "This object specifies the suppression of CDRs for
        prepaid.
        
        This object can be set to 'true' only when the object
        cgprsCgProfileCdrSuppress is set to 'false'.
        
        If set to 'true', there won't be any CDRs generated
        for prepaid users.
        
        If set to 'false', the CDRs will be generated for
        prepaid users."
    DEFVAL { false }
    ::= { cgprsCgProfileEntry 12 }

cgprsCgProfileContentDccaProfile OBJECT-TYPE
    SYNTAX SnmpAdminString
--    Rsyntax OCTET STRING(SIZE(0..255))
    ACCESS read-write
    STATUS mandatory
    DESCRIPTION
        "This object specifies a DCCA client to use to communicate 
        with a DCCA server in a GGSN charging profile.
        
        The profile name is the DCCA profile name 
        (cGgsnSADccaProfileName) which is present in  
        CISCO-GGSN-SERVICE-AWARE-MIB and it's outside the scope of 
        this MIB. 
        
        The presence of the object in this table indicates online 
        billing is required. Therefore, regardless of whether a 
        subscriber is prepaid or postpaid, the GGSN will contact 
        the DCCA server if this object is set.
        
        If the user is to be treated as a postpaid user, the server 
        returns X and the user is treated as a postpaid user. If 
        this object is not set to valid value, then users using the 
        charging profile will be treated as postpaid (offline 
        billing)."
    ::= { cgprsCgProfileEntry 13 }

cgprsCgProfileContentPostTime OBJECT-TYPE
    SYNTAX Gauge(300..4294967295)
--  Units
--    seconds
    ACCESS read-write
    STATUS mandatory
    DESCRIPTION
        "This object specifies a trigger condition for postpaid 
        users in this charging profile, the time duration limit 
        that when exceeded causes the GGSN to collect upstream 
        and downstream traffic byte counts and close and update 
        the G-CDR for a particular PDP context."
    ::= { cgprsCgProfileEntry 14 }

cgprsCgProfileContentPostValTime OBJECT-TYPE
    SYNTAX Gauge(900..4294967295)
--  Units
--    seconds
    ACCESS read-write
    STATUS deprecated
    DESCRIPTION
        "This object specifies the validity timeout for this 
        postpaid users in this charging profile. By default, the
        time and volume quota for postpaid has no validity timeout.
        If it is configured, it applies to both time based or volume 
        based quota.  This object is deprecated by 
        cgprsCgProfileContentPostValidityTime"
    ::= { cgprsCgProfileEntry 15 }

cgprsCgProfileContentPostVolume OBJECT-TYPE
    SYNTAX Gauge(1..4294967295)
--  Units
--    bytes
    ACCESS read-write
    STATUS mandatory
    DESCRIPTION
        "This object specifies a trigger condition for postpaid 
        users in this charging profile, the maximum number of 
        bytes that the GGSN maintains across all containers for 
        a particular PDP context before closing and updating 
        the G-CDR."
    ::= { cgprsCgProfileEntry 16 }

cgprsCgProfileContentRulebaseId OBJECT-TYPE
    SYNTAX SnmpAdminString
--    Rsyntax OCTET STRING(SIZE(0..255))
    ACCESS read-write
    STATUS mandatory
    DESCRIPTION
        "This object sets the rulebase ID for this charging profile.
        
        Rulebases contain the rules for defining categories of 
        traffic, categories on which decisions such as whether to 
        allow or disallow traffic, and how to measure the traffic, 
        are based. The GGSN maps Diameter Rulebase IDs to CSG 
        billing plans.
        
        The rulebase value presented in a RADIUS Access Accept 
        message overrides the default rulebase ID configured in 
        the charging profile. A rulebase ID received in a CCA 
        initial message from a DCCA server overrides the Rulebase 
        ID received from the RADIUS server and the default rulebase 
        ID configured in a charging profile."
    ::= { cgprsCgProfileEntry 17 }

cgprsCgProfileContentPostQosChange OBJECT-TYPE
    SYNTAX TruthValue
--    Rsyntax INTEGER {
--        true(1),
--        false(2)
--        }
    ACCESS read-write
    STATUS mandatory
    DESCRIPTION
        "This object when set to 'true' enables the trigger for QoS 
        change for postpaid users using this charging profile. 
        
        The change in QoS causes GGSN to close the G-CDR for a 
        particular PDP context and generate the service record for each
        service."
    DEFVAL { false }
    ::= { cgprsCgProfileEntry 18 }

cgprsCgProfileContentPostSgsnChange OBJECT-TYPE
    SYNTAX TruthValue
--    Rsyntax INTEGER {
--        true(1),
--        false(2)
--        }
    ACCESS read-write
    STATUS mandatory
    DESCRIPTION
        "This object when set to 'true' enables the trigger for SGSN 
        change for postpaid users using this charging profile.  The
        SGSN address is added to the SGSN list in the context G-CDR.
        
        When the SGSN limit is reached, the G-CDR is closed. Current
        SGSN address is written into the CDR, when the cgprsCgRelease  
        value is 'release4' or above, and service record is 
        generated."
    DEFVAL { false }
    ::= { cgprsCgProfileEntry 19 }

cgprsCgProfileContentPostRatChange OBJECT-TYPE
    SYNTAX TruthValue
--    Rsyntax INTEGER {
--        true(1),
--        false(2)
--        }
    ACCESS read-write
    STATUS mandatory
    DESCRIPTION
        "This object when set to 'true' enables the trigger for RAT
        change for postpaid users using this charging profile.
        
        This object can be set to 'true' only when the object 
        cgprsCgServiceRecordIncludeRat is 'true'.
        
        When a RAT change is received, the G-CDR is closed. The new 
        RAT value is written into the new G-CDR and service record is
        is generated with the new RAT value."
    DEFVAL { false }
    ::= { cgprsCgProfileEntry 20 }

cgprsCgProfileContentPostPlmnChange OBJECT-TYPE
    SYNTAX TruthValue
--    Rsyntax INTEGER {
--        true(1),
--        false(2)
--        }
    ACCESS read-write
    STATUS mandatory
    DESCRIPTION
        "This object when set to 'true' enables the trigger for PLMN 
        change for postpaid users using this charging profile.  When 
        enabled, the current PLMN-ID is always written into the 
        service-record.  If none is received in the PDP create/update 
        request, a value of zero is written into the service-record.
        
        This object can be set to 'true' only when the object 
        cgprsCgServiceRecordIncludePlmn is 'true'.
        
        When a PLMN-ID change is received, the G-CDR is closed. 
        A new service-record is generated and the new PLMN-ID is 
        written into the new service-record."
    DEFVAL { false }
    ::= { cgprsCgProfileEntry 21 }

cgprsCgProfileStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row.
        Conceptual rows having the value 'permanent' need not
        allow write-access to any columnar objects in the row."
    DEFVAL { nonVolatile }
    ::= { cgprsCgProfileEntry 22 }

cgprsCgProfileContentPostValidityTime OBJECT-TYPE
    SYNTAX Gauge(0|900..4294967295)
--  Units
--    seconds
    ACCESS read-write
    STATUS mandatory
    DESCRIPTION
        "This object specifies the validity timeout for this
        postpaid users in this charging profile. By default, the
        time and volume quota for postpaid has no validity timeout.
        If it is configured, it applies to both time based or volume
        based quota.  The valid range of this object is from 900 to
        4294967295, and the value 0 indicates that the validity
        timeout is not configured."
    DEFVAL { 0 }
    ::= { cgprsCgProfileEntry 23 }

cgprsCgProfileMapTable OBJECT-TYPE
    SYNTAX SEQUENCE OF CgprsCgProfileMapEntry
    ACCESS not-accessible
    STATUS mandatory
    DESCRIPTION
        "This table maintains the default charging profile
        mappings. The profile set in cgprsCgProfileTable will
        be mapped to the default profile table. Only one
        mapping to the type of MS can be present.
        
        This is a static table which contains only four entries,
        each for a category."
    ::= { ciscoGprsChargingConfig 31 }

cgprsCgProfileMapEntry OBJECT-TYPE
    SYNTAX CgprsCgProfileMapEntry
    ACCESS not-accessible
    STATUS mandatory
    DESCRIPTION
        "Entry for each category (all, home, visiting and roamer) 
        exists, which has the profile number and override 
        condition."
    INDEX { cgprsCgProfileMapCategory }
    ::= { cgprsCgProfileMapTable 1 }

CgprsCgProfileMapEntry ::= SEQUENCE {
    cgprsCgProfileMapCategory INTEGER,
    cgprsCgProfileMapNum INTEGER,
    cgprsCgProfileMapOverride TruthValue,
    cgprsCgProfileMapTrusted TruthValue,
    cgprsCgProfileMapNumber INTEGER
    }

cgprsCgProfileMapCategory OBJECT-TYPE
    SYNTAX INTEGER {
        any(1),
        home(2),
        roaming(3),
        visitor(4)
        }
    ACCESS not-accessible
    STATUS mandatory
    DESCRIPTION
        "This object defines the category in which the MS
        falls into."
    ::= { cgprsCgProfileMapEntry 1 }

cgprsCgProfileMapNum OBJECT-TYPE
    SYNTAX INTEGER(0..65535)
    ACCESS read-write
    STATUS deprecated
    DESCRIPTION
        "This object represents the profile number which is
        created using cgprsCgProfileTable. This object holds the
        valid value represented by cgprsCgProfileNum. The profile 
        number 0 cannot be created or deleted using 
        cgprsCgProfileTable. It's created using the other 
        configuration objects cgprsCgContainerVolThresh, 
        cgprsCgCdrSgsnChangeLimit, cgprsCgContainerTimeLimit.
        This object is deprecated by cgprsCgProfileMapNumber."
    DEFVAL { 0 }
    ::= { cgprsCgProfileMapEntry 2 }

cgprsCgProfileMapOverride OBJECT-TYPE
    SYNTAX TruthValue
--    Rsyntax INTEGER {
--        true(1),
--        false(2)
--        }
    ACCESS read-write
    STATUS mandatory
    DESCRIPTION
        "This object defines whether the profile set in
        cgprsCgProfileMapNum should override the value received 
        from SGSN."
    DEFVAL { false }
    ::= { cgprsCgProfileMapEntry 3 }

cgprsCgProfileMapTrusted OBJECT-TYPE
    SYNTAX TruthValue
--    Rsyntax INTEGER {
--        true(1),
--        false(2)
--        }
    ACCESS read-write
    STATUS mandatory
    DESCRIPTION
        "This object defines whether the profile for 'roaming',
        'visitor' is a trusted. This object has no meaning when
        the value of the cgprsCgProfileMapCategory is 'all' or
        'home'.
        
        If this object is set to 'true' and cgprsCgProfileMapCategory
        is 'roaming', then this profile will be the default profile
        for trusted roamer. If set to 'false', then it's just a
        roamer.
        
        If this object is set to 'true' and cgprsCgProfileMapCategory
        is 'visitor', then this profile will be the default profile
        for trusted visitor. If set to 'false', then it's just a
        roamer."
    DEFVAL { false }
    ::= { cgprsCgProfileMapEntry 4 }

cgprsCgProfileMapNumber OBJECT-TYPE
    SYNTAX INTEGER(-1..65535)
    ACCESS read-write
    STATUS mandatory
    DESCRIPTION
        "This object represents the profile number which is
        created using cgprsCgProfileTable. This object holds the
        valid value represented by cgprsCgProfileNum. The profile
        number 0 cannot be created or deleted using
        cgprsCgProfileTable. It's created using the other
        configuration objects cgprsCgContainerVolThresh,
        cgprsCgCdrSgsnChangeLimit, cgprsCgContainerTimeLimit.
        The value -1 for this object indicates that the default
        profile for the category is not configured."
    DEFVAL { -1 }
    ::= { cgprsCgProfileMapEntry 5 }

cgprsCgChargingCharReject OBJECT-TYPE
    SYNTAX TruthValue
--    Rsyntax INTEGER {
--        true(1),
--        false(2)
--        }
    ACCESS read-write
    STATUS mandatory
    DESCRIPTION
        "This object defines whether the incoming PDP create
        request has to be rejected or accepted depending on
        the charging profile match.
        
        If in case a PDP create request comes in and if there
        is no matching profile configured and there is no
        overriding profile set, then if this object is set to
        'false', the PDP will be accepted and the default
        profile will be applied to it. If this object is set
        to 'true', the PDP will be rejected if no matching
        profile in the create request or overriding profile is
        present."
    DEFVAL { false }
    ::= { ciscoGprsChargingConfig 32 }

cgprsCgServiceMode OBJECT-TYPE
    SYNTAX INTEGER {
        operational(1),
        maintenance(2)
        }
    ACCESS read-write
    STATUS mandatory
    DESCRIPTION
        "This object specifies the service mode for charging. The 
        charging functions in the GGSN involve mainly 
        collection/accumulation of CDRs and transmitting CDRs to the
        Charging Gateways. The charging service-mode function has no 
        impact to the collection/accumulation of CDRs. The charging 
        service mode function only involves the transmission of CDRs 
        to the charging gateways. The charging service-mode has the 
        following two states:
        
        'operational' : Normal operation.
        'maintenance' : In this state, transmission of CDRs to the 
                        charging gateways will not be performed; 
                        However, collection and accumulation of CDRs 
                        will continue as is done normally.
        
        The default charging service-mode state is 'in-service'(This
        mode is set with value as 'operational'). When the GGSN is in
        'outOfService' mode set in cGgsnServiceMode, all the charging 
        configurations will be allowed. In the system-init phase, 
        the charging service mode CLI configs will not be handled. 
        
        The handling of 'Redirecting Request', 'Node Alive' and 
        charging gateway switchover mechanisms will not be performed 
        while the charging is in maintenance mode. After the mode is 
        changed to in-service, the messages in the pending queue will 
        be sent towards the newly configured active charging gateway 
        and the normal functions will continue from thereon.
        
        When switching between modes, traps will be generated using
        cgprsCgInServiceModeNotif and cgprsCgMaintenanceModeNotif."
    DEFVAL { operational }
    ::= { ciscoGprsChargingConfig 33 }

cgprsCgPartialCdrGenEnable OBJECT-TYPE
    SYNTAX TruthValue
--    Rsyntax INTEGER {
--        true(1),
--        false(2)
--        }
    ACCESS read-write
    STATUS mandatory
    DESCRIPTION
        "A Primary CDR refers to the first CDR for a PDP. Subsequent
        CDR's, called secondary CDR's, will be opened when the primary
        CDR is closed by triggers like exceeding data volume limit,
        max number of charging condition changes, SGSN change, etc.,
        A Partial CDR is such subsequent CDR in which some fields, like
        Access Point Name, PDP Type, etc., that cannot change during
        the life time of the PDP are not included. This object controls
        the generation of partial CDRs on GGSN. When set to 'true',
        partial CDR's are generated. When set to 'false', partial CDR's
        are not generated i.e., all the fields are sent in the CDR."
    DEFVAL { true }
    ::= { ciscoGprsChargingConfig 34 }

cgprsCgSwitchOverPriority OBJECT-TYPE
    SYNTAX TruthValue
--    Rsyntax INTEGER {
--        true(1),
--        false(2)
--        }
    ACCESS read-write
    STATUS mandatory
    DESCRIPTION
        "This object is used to enable the switch over priority
        mechanism. 
        
        'true'  - If a higher priority CG comes up, it becomes the 
                  active CG.
        
        'false' - If a higher priority CG comes up, the existing
                  active CG continues to be active."
    DEFVAL { false }
    ::= { ciscoGprsChargingConfig 35 }

cgprsCgCharSelectionMode OBJECT-TYPE
    SYNTAX TruthValue
--    Rsyntax INTEGER {
--        true(1),
--        false(2)
--        }
    ACCESS read-write
    STATUS mandatory
    DESCRIPTION
        "This object is used to add the charging characteristic
        selection mode in the CDR.
        
        'true'  - Charging characteristic selection mode will be 
                  added in the CDR.
        'false' - Charging characteristic selection mode will not
                  be added in the CDR."
    DEFVAL { false }
    ::= { ciscoGprsChargingConfig 36 }

cgprsCgReconnect OBJECT-TYPE
    SYNTAX INTEGER(0..600)
--  Units
--    minutes
    ACCESS read-write
    STATUS mandatory
    DESCRIPTION
        "This object enables the charging reconnect feature.
        
        This feature when enabled, reconnects to the CG that is 
        unreachable due to some transient network or link failures. 
        It is only needed for CG using path protocoal as UDP and 
        when the CG can only respond to echo but cannot send echo 
        request. 
        
        By default this feature is disabled."
    DEFVAL { 0 }
    ::= { ciscoGprsChargingConfig 37 }

cgprsCgPtcEnable OBJECT-TYPE
    SYNTAX TruthValue
--    Rsyntax INTEGER {
--        true(1),
--        false(2)
--        }
    ACCESS read-write
    STATUS mandatory
    DESCRIPTION
        "When this object is set, GGSN  sends the Packet Transfer 
        Command (PTC) IE in the CDR message.
        
        'true' - send PTC IE with the CDR. The value in the 
                 IE will be 'Send Data Record Packet' if the
                 object cgprsCgPtcPossiblyDupEnable is not set
                 to 'true' and there is no condition of possibly
                 duplicate scenario. 
        'false' - do not send PTC IE with the CDR.
        
        This object cannot be set to 'false' if the object
        cgprsCgPtcPossiblyDupEnable is set to 'true'."
    REFERENCE
        "GSM 12.15 version 7.6.0 Release 1998"
    DEFVAL { false }
    ::= { ciscoGprsChargingConfig 38 }

cgprsCgPtcPossiblyDupEnable OBJECT-TYPE
    SYNTAX TruthValue
--    Rsyntax INTEGER {
--        true(1),
--        false(2)
--        }
    ACCESS read-write
    STATUS mandatory
    DESCRIPTION
        "This object is used to send possibly duplicated Data Record 
        Packet. When the CDR packet is directed to a secondary CGF 
        (by a CDR generating node) because the currently used CGF 
        is not working or the CDR transfer is not working properly, 
        then this Packet Transfer Command is used instead of the 
        normal 'Send Data Record Packet'.  
        
        This object has no meaning unless the object cgprsCgPtcEnable
        is set to 'true'.
        
        'true' - send PTC IE with 'Possibly Duplicate Record' with
                 the CDR when the possibly duplicate scenario occurs.
        'false' - Do not set the PTC IE with 'Possibly Duplicate
                  Record' even if possibly duplicate scenario occurs."
    REFERENCE
        "GSM 12.15 version 7.6.0 Release 1998"
    DEFVAL { false }
    ::= { ciscoGprsChargingConfig 39 }

cgprsCgCdrOptionServiceRecord OBJECT-TYPE
    SYNTAX Gauge(0..100)
    ACCESS read-write
    STATUS mandatory
    DESCRIPTION
        "G-CDRs contain information for part, or the entire 
        duration, of a PDP context. The G-CDR includes information 
        such as the subscriber (MSISDN, IMSI), APN used, QoS 
        applied, SGSN ID (as the mobile access location), a time 
        stamp and duration, data volume recorded separately for 
        the upstream and downstream direction, and volume thresholds 
        for intermediate CDR generation and tariff time switches.
        
        In addition to all of the above, additionally, enhanced 
        G-CDRs contain a service-record part that contains the usage 
        data of each service flow used by a PDP session (specified 
        by category ID). For example, the upstream and downstream 
        volume and duration is recorded per service flow.
        
        By default this feature is not enabled.
        
        The number specified is the maximum number of service records 
        a G-CDR can contain before the G-CDR is closed and a partial 
        G-CDR is opened."
    DEFVAL { 0 }
    ::= { ciscoGprsChargingConfig 40 }

cgprsCgPartialCdrGenEnableAll OBJECT-TYPE
    SYNTAX TruthValue
--    Rsyntax INTEGER {
--        true(1),
--        false(2)
--        }
    ACCESS read-write
    STATUS mandatory
    DESCRIPTION
        "This object when set to 'true' enables the GGSN to copy
        the SGSN list for charging release prior to release 4 
        (cgprsCgRelease). The SGSN change limit trigger 
        specified in the object cgprsCgCdrSgsnChangeLimit has to be
        set as well.
        
        If this object is set to 'false'-current SGSN address may not
        be present in CDR.
        
        This object can be set to true only when the object
        cgprsCgPartialCdrGenEnable is set to 'true'."
    DEFVAL { false }
    ::= { ciscoGprsChargingConfig 41 }

cgprsCgCdrOptionApn OBJECT-TYPE
    SYNTAX TruthValue
--    Rsyntax INTEGER {
--        true(1),
--        false(2)
--        }
    ACCESS read-write
    STATUS mandatory
    DESCRIPTION
        "This object when set to 'true' includes real APN in the 
        G-CDR and accounting records.
        
        If object is set to 'false'- Access Point Name is 
        disabled in G-CDRs. The option cannot be disabed if the 
        CHARGING_RELEASE is 98 or 99."
    DEFVAL { true }
    ::= { ciscoGprsChargingConfig 42 }

cgprsCgCdrOptionVirtualApn OBJECT-TYPE
    SYNTAX TruthValue
--    Rsyntax INTEGER {
--        true(1),
--        false(2)
--        }
    ACCESS read-write
    STATUS mandatory
    DESCRIPTION
        "This object when set to 'true' includes virtual APN in 
        G-CDR and accounting records.
        
        If this object is set to 'false'- Real APN is included in the
        G-CDRs."
    DEFVAL { false }
    ::= { ciscoGprsChargingConfig 43 }

cgprsCgCdrOptionApnSelMode OBJECT-TYPE
    SYNTAX TruthValue
--    Rsyntax INTEGER {
--        true(1),
--        false(2)
--        }
    ACCESS read-write
    STATUS mandatory
    DESCRIPTION
        "This object when set to 'true' includes 'APN selection mode'
        field in G-CDR and sent to CG. 
        
        The field 'APN selection mode' indicates how the SGSN selected
        the APN to be used. Selection Mode indicates whether a 
        subscribed APN was selected, or whether a non subscribed APN 
        sent by the MS, or a non-subscribed APN chosen by SGSN was
        was selected."
    DEFVAL { false }
    ::= { ciscoGprsChargingConfig 44 }

cgprsCgCdrOptionDynamicAddr OBJECT-TYPE
    SYNTAX TruthValue
--    Rsyntax INTEGER {
--        true(1),
--        false(2)
--        }
    ACCESS read-write
    STATUS mandatory
    DESCRIPTION
        "This object when set to 'true' includes 'Dynamic Address' 
        field in G-CDR and sent to CG.
        
        This field indicates that PDP address has been dynamically 
        allocated for that particular PDP context. This field is
        missing if address is static i.e. part of PDP context 
        subscription."
    DEFVAL { true }
    ::= { ciscoGprsChargingConfig 45 }

cgprsCgCdrOptionNip OBJECT-TYPE
    SYNTAX TruthValue
--    Rsyntax INTEGER {
--        true(1),
--        false(2)
--        }
    ACCESS read-write
    STATUS mandatory
    DESCRIPTION
        "This object when set to 'true' includes NIP (Network
        Initiated PDP context) field in G-CDR and sent to CG.
        
        This field indicates that PDP context is network initiated.
        The field is missing in case of mobile activated PDP context."
    DEFVAL { true }
    ::= { ciscoGprsChargingConfig 46 }

cgprsCgCdrOptionPdpAddress OBJECT-TYPE
    SYNTAX TruthValue
--    Rsyntax INTEGER {
--        true(1),
--        false(2)
--        }
    ACCESS read-write
    STATUS mandatory
    DESCRIPTION
        "This object when set to 'true' includes 'Served PDP Address'
        field in G-CDR and sent to CG. 
        
        This field (Served PDP Address) contains the PDP address 
        of the served IMSI. This is a network layer address 
        i.e. of type IP version 4 or IP version 6. This parameter 
        shall be present except when both the PDP type is PPP and 
        dynamic PDP address assignment is used."
    DEFVAL { true }
    ::= { ciscoGprsChargingConfig 47 }

cgprsCgCdrOptionPdpType OBJECT-TYPE
    SYNTAX TruthValue
--    Rsyntax INTEGER {
--        true(1),
--        false(2)
--        }
    ACCESS read-write
    STATUS mandatory
    DESCRIPTION
        "This object if set to 'true' includes 'PDP Type' field 
        in G-CDRs.   
        
        This field defines the PDP type,e.g.IP,PPP or IHOSS:OSP."
    DEFVAL { true }
    ::= { ciscoGprsChargingConfig 48 }

cgprsCgCdrOptionSerMsisdn OBJECT-TYPE
    SYNTAX TruthValue
--    Rsyntax INTEGER {
--        true(1),
--        false(2)
--        }
    ACCESS read-write
    STATUS mandatory
    DESCRIPTION
        "This object when set to 'true' enable the GGSN to provide
        the MSISDN number from the create PDP context request
        in the G-CDRs.
        
        This field contains the Mobile Station (MS) ISDN number 
        (MSISDN) of the served party. The term 'served' party is
        used to describe the mobile subscriber involved in the 
        transaction recorded.
        
        If the object is set to 'false', Disable the GGSN to provide
        MSISDN number in the G-CDRs."
    DEFVAL { false }
    ::= { ciscoGprsChargingConfig 49 }

cgprsCgCdrOptionSgsnPlmn OBJECT-TYPE
    SYNTAX TruthValue
--    Rsyntax INTEGER {
--        true(1),
--        false(2)
--        }
    ACCESS read-write
    STATUS mandatory
    DESCRIPTION
        "This object whe set to 'true' includes SGSN PLMN ID 
        (MCC and MNC) in the G-CDR and sent to CG. 
        
        The SGSN PLMN ID field contains a SGSN PLMN Identifier, 
        for the SGSNs which have been connected during the record. 
        This implies that when the MS moves to another PLMN, the G-CDR
        has to be closed."
    DEFVAL { false }
    ::= { ciscoGprsChargingConfig 50 }

cgprsCgCdrOptionCamelCharInfo OBJECT-TYPE
    SYNTAX TruthValue
--    Rsyntax INTEGER {
--        true(1),
--        false(2)
--        }
    ACCESS read-write
    STATUS mandatory
    DESCRIPTION
        "This object if set to 'true', S-CDR CAMEL information 
        recieved from SGSN, which is a copy of Tag and Length 
        from SGSN's CDR (S-CDR) is included in G-CDR. 
        
        If this object is set to 'false', CAMEL field is not 
        included in G-CDRs."
    REFERENCE
        "3GPP;Technical Specification Group Services and System 
        Aspects;Telecommunication Management;Charging Management;
        Charging data description for the Packet Switched (PS) domain
        (Release 5); 3GPP TS 32.215 V5.7.0"
    DEFVAL { false }
    ::= { ciscoGprsChargingConfig 51 }

cgprsCgCdrOptionImeisv OBJECT-TYPE
    SYNTAX TruthValue
--    Rsyntax INTEGER {
--        true(1),
--        false(2)
--        }
    ACCESS read-write
    STATUS mandatory
    DESCRIPTION
        "This object when set to 'true' the IMEI (Software Version)
        IE shall be handled by GGSN in a transparent manner and shall 
        be sent to the Charging gateway that is release 5.0 compliant
        without any modification. 
        
        International Mobile Equipment Identity IMEI Software Version 
        (IMEISV): indicates identity of mobile equipment used by the 
        subscriber."
    DEFVAL { false }
    ::= { ciscoGprsChargingConfig 52 }

cgprsCgCdrOptionMsTimeZone OBJECT-TYPE
    SYNTAX TruthValue
--    Rsyntax INTEGER {
--        true(1),
--        false(2)
--        }
    ACCESS read-write
    STATUS mandatory
    DESCRIPTION
        "This object when set to 'true' includes MS Time Zone field 
        in the G-CDRs and sent to CG.
        
        MS Time Zone indicates the offset between universal time
        and local time in steps of 15 minutes of where the MS currently
        resides."
    DEFVAL { false }
    ::= { ciscoGprsChargingConfig 53 }

cgprsCgCdrOptionRatType OBJECT-TYPE
    SYNTAX TruthValue
--    Rsyntax INTEGER {
--        true(1),
--        false(2)
--        }
    ACCESS read-write
    STATUS mandatory
    DESCRIPTION
        "This object when set to 'true' includes Radio Access Type
        (RAT) IE in the G-CDRs and sent to CG.
        
        RAT, indicates whether the SGSN serves the User Equipment
        (UE) by Universal Terrestrial Radio Access Network (UTRAN)
        or GSM/EDGE RAN (GERAN)."
    DEFVAL { false }
    ::= { ciscoGprsChargingConfig 54 }

cgprsCgCdrOptionUserLocInfo OBJECT-TYPE
    SYNTAX TruthValue
--    Rsyntax INTEGER {
--        true(1),
--        false(2)
--        }
    ACCESS read-write
    STATUS mandatory
    DESCRIPTION
        "This object when set to 'true' includes the User Location 
        Information IE in G-CDRs and sent to CG.
        
        User Location Information gives Cell Global Identity
        (CGI)/Service Area Identity (SAI) of where the MS is
        currently located."
    DEFVAL { false }
    ::= { ciscoGprsChargingConfig 55 }

cgprsCgServiceRecordIncludeRat OBJECT-TYPE
    SYNTAX TruthValue
--    Rsyntax INTEGER {
--        true(1),
--        false(2)
--        }
    ACCESS read-write
    STATUS mandatory
    DESCRIPTION
        "This object when set to 'true', writes the RAT value into 
        into the service record when RAT change is recieved.
        
        If this object is set to 'false', it disables the RAT trigger 
        set by the object cgprsCgProfileContentPostRatChange."
    DEFVAL { false }
    ::= { ciscoGprsChargingConfig 56 }

cgprsCgServiceRecordIncludePlmn OBJECT-TYPE
    SYNTAX TruthValue
--    Rsyntax INTEGER {
--        true(1),
--        false(2)
--        }
    ACCESS read-write
    STATUS mandatory
    DESCRIPTION
        "This object when set to 'true', writes the PLMN-ID of the 
        PDP into the service record when there is change in the
        PLMN-ID.
        
        If this object is set to 'false', it disables the plmn trigger 
        set by the object cgprsCgProfileContentPostPlmnChange."
    DEFVAL { false }
    ::= { ciscoGprsChargingConfig 57 }

cgprsCgDownTimes OBJECT-TYPE
    SYNTAX Counter
--  Units
--    transitions
    ACCESS read-only
    STATUS mandatory
    DESCRIPTION
        "The number of occurrences of cgprsCgAlarmEchoFailure 
        traps state transitions since system startup.
        
        Trigger Condition: This counter is triggered when
        the GGSN detects a CG has gone down.
        Condition includes, 
          a) Link state down.
          b) Redirection request."
    ::= { ciscoGprsChargingStats 1 }

cgprsCgAccPtNum OBJECT-TYPE
    SYNTAX Counter
--  Units
--    access-points
    ACCESS read-only
    STATUS mandatory
    DESCRIPTION
        "The number of access points for which charging data  
        is being collected.
        
        Trigger Condition: This counter is triggered when a
        CDR is opened for a PDP and that PDP belongs to a new
        APN."
    ::= { ciscoGprsChargingStats 2 }

cgprsCgCdrOpenedNum OBJECT-TYPE
    SYNTAX Gauge
--  Units
--    CDRs
    ACCESS read-only
    STATUS mandatory
    DESCRIPTION
        "The number of currently opened G-CDRs on the GGSN. 
        A G-CDR shall be opened for each activated PDP context.
        
        Trigger Condition: This counter is triggered when a new 
        CDR is opened. This new CDR might be opened initially and 
        also due to the closure of the existing opened CDR."
    ::= { ciscoGprsChargingStats 3 }

cgprsCgCdrClosedNum OBJECT-TYPE
    SYNTAX Gauge
--  Units
--    CDRs
    ACCESS read-only
    STATUS mandatory
    DESCRIPTION
        "The number of currently closed G-CDRs on the GGSN 
        which have not been sent to the CG. 
        The G-CDR shall be closed on encountering some trigger  
        conditions. In the event that the G-CDR is closed and the
        PDP remains active, a new G-CDR will be opened for the PDP.
        
        Trigger Condition: This counter is triggered when the CDR 
        is closed. The closure might be due to different trigger 
        conditions.
            a) Clearing of the CDR using CLI.
            b) Tigger conditions like vloume limit, time limit, 
               sgsn change limit, container change limit 
               set with configuration objects.
            c) CDR size reaches maximum."
    ::= { ciscoGprsChargingStats 4 }

cgprsCgContainerNum OBJECT-TYPE
    SYNTAX Gauge
--  Units
--    containers
    ACCESS read-only
    STATUS mandatory
    DESCRIPTION
        "The number of currently open or closed charging containers.
        
        Trigger Condition: This counter is triggered when the CDR 
        is closed or the CDR is updated."
    ::= { ciscoGprsChargingStats 5 }

cgprsCgPendingMsgNum OBJECT-TYPE
    SYNTAX Gauge
--  Units
--    messages
    ACCESS read-only
    STATUS mandatory
    DESCRIPTION
        "The number of currently pending G-CDR output messages.
        
        Trigger Condition: This counter is triggered when the CDR 
        is sent to the CG and the response from the CG failed."
    ::= { ciscoGprsChargingStats 6 }

cgprsCgSentMsgNum OBJECT-TYPE
    SYNTAX Counter
--  Units
--    messages
    ACCESS read-only
    STATUS mandatory
    DESCRIPTION
        "The number of transmitted G-CDR output messages since 
        the charging service is enabled. The sent G-CDR is 
        the CDR that was sent to the CG for which the GGSN 
        got a response back from the CG.
        
        Trigger Condition: This counter is triggered when a CDR 
        is sent to the CG and got a positive response."
    ::= { ciscoGprsChargingStats 7 }

cgprsCgTotalCdrOpened OBJECT-TYPE
    SYNTAX Counter
--  Units
--    CDRs
    ACCESS read-only
    STATUS mandatory
    DESCRIPTION
        "This object gives the total number of CDRs opened on the 
        GGSN, either since system startup or since the last time the 
        charging statistics was cleared.
        
        Trigger Condition: This counter is triggered when a new CDR 
        is opened. This new CDR might be opened initially and also 
        due to the closure of the existing opened CDR."
    ::= { ciscoGprsChargingStats 8 }

cgprsCgTotalContainerCreated OBJECT-TYPE
    SYNTAX Counter
--  Units
--    containers
    ACCESS read-only
    STATUS mandatory
    DESCRIPTION
        "This object gives the total number of containers created on 
        the GGSN, either since system startup or since the last time 
        the charging statistics was cleared.
        
        Trigger Condition: This counter is triggered when the CDR is 
        closed or the CDR is updated."
    ::= { ciscoGprsChargingStats 9 }

cgprsCgTotalServiceRecords OBJECT-TYPE
    SYNTAX Counter
--  Units
--    records
    ACCESS read-only
    STATUS mandatory
    DESCRIPTION
        "This object reflects the total number of service records
        created on the GGSN, either since the system startup or since
        the time the service aware feature is enabled.
        
        Trigger Condition: This counter is triggered when the
        service record is closed."
    ::= { ciscoGprsChargingStats 10 }

cgprsCgActiveChgGatewayAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object specifies the address type of the active 
        charging gateway."
    ::= { ciscoGprsChargingStatus 1 }

cgprsCgActiveChgGatewayAddress OBJECT-TYPE
    SYNTAX InetAddress
--    Rsyntax OCTET STRING(SIZE(0..255))
    ACCESS read-only
    STATUS mandatory
    DESCRIPTION
        "This object specifies the address of the active charging
        gateway.
        
        The type of address will be represented by
        cgprsCgActiveChgGatewayAddrType."
    ::= { ciscoGprsChargingStatus 2 }

cgprsCgOldChgGatewayAddress OBJECT-TYPE
    SYNTAX InetAddress
--    Rsyntax OCTET STRING(SIZE(0..255))
    ACCESS read-only
    STATUS mandatory
    DESCRIPTION
        "This object specifies the address of the previous active
        charging gateway.
        The type of address will same as the one present in 
        cgprsCgActiveChgGatewayAddrType."
    ::= { ciscoGprsChargingStatus 3 }

cgprsCgAlarmEnable OBJECT-TYPE
    SYNTAX TruthValue
--    Rsyntax INTEGER {
--        true(1),
--        false(2)
--        }
    ACCESS read-write
    STATUS mandatory
    DESCRIPTION
        "The object controls the generation of 
        cgprsCgAlarmNotif as follows:
         'true(1)' - the generation of cgprsCgAlarmNotif 
                     notifications is enabled.
         'false(2)' - the generation of cgprsCgAlarmNotif 
                     notifications is disabled. "
    ::= { ciscoGprsChargingAlarms 1 }

cgprsCgAlarmHistTableMax OBJECT-TYPE
    SYNTAX Gauge(1..4294967295)
    ACCESS read-write
    STATUS mandatory
    DESCRIPTION
        "Specifies the upper limit on the number of entries 
        that the cgprsCgAlarmHistTable  may contain."
    DEFVAL { 500 }
    ::= { ciscoGprsChargingAlarms 2 }

cgprsCgAlarmHistTable OBJECT-TYPE
    SYNTAX SEQUENCE OF CgprsCgAlarmHistEntry
    ACCESS not-accessible
    STATUS mandatory
    DESCRIPTION
        "This table contains a history of all
        charging gateway and charging related alarms that 
        were generated."
    ::= { ciscoGprsChargingAlarms 3 }

cgprsCgAlarmHistEntry OBJECT-TYPE
    SYNTAX CgprsCgAlarmHistEntry
    ACCESS not-accessible
    STATUS mandatory
    DESCRIPTION
        "The information regarding a CG alarm.
        An entry, the oldest entry, is removed if the 
        table is full and a new entry is created 
        in the table to accommodate a new alarm."
    INDEX { cgprsCgAlarmHistIndex }
    ::= { cgprsCgAlarmHistTable 1 }

CgprsCgAlarmHistEntry ::= SEQUENCE {
    cgprsCgAlarmHistIndex Gauge,
    cgprsCgAlarmHistType CgprsCgAlarmType,
    cgprsCgAlarmHistAddrType InetAddressType,
    cgprsCgAlarmHistAddress InetAddress,
    cgprsCgAlarmHistSeverity CiscoAlarmSeverity,
    cgprsCgAlarmHistInfo SnmpAdminString
    }

cgprsCgAlarmHistIndex OBJECT-TYPE
    SYNTAX Gauge(1..4294967295)
    ACCESS not-accessible
    STATUS mandatory
    DESCRIPTION
        "A monotonically increasing integer for the sole purpose 
        of indexing the charging gateway and charging related alarms. 
        When the index reaches the maximum value it will wrap around 
        to one."
    ::= { cgprsCgAlarmHistEntry 1 }

cgprsCgAlarmHistType OBJECT-TYPE
    SYNTAX CgprsCgAlarmType
--    Rsyntax INTEGER {
--        cgprsCgAlarmCgDown(1),
--        cgprsCgAlarmCgUp(2),
--        cgprsCgAlarmTransFailure(3),
--        cgprsCgAlarmTransSuccess(4),
--        cgprsCgAlarmCapacityFull(5),
--        cgprsCgAlarmCapacityFree(6),
--        cgprsCgAlarmEchoFailure(7),
--        cgprsCgAlarmEchoRestored(8),
--        cgprsCgAlarmCdrDiscard(9),
--        cgprsCgAlarmCdrBuffered(10),
--        cgprsCgAlarmChargingDisabled(11),
--        cgprsCgAlarmChargingEnabled(12)
--        }
    ACCESS read-only
    STATUS mandatory
    DESCRIPTION
        "Type of the GPRS charging gateway or charging related
        alarm."
    ::= { cgprsCgAlarmHistEntry 2 }

cgprsCgAlarmHistAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object indicates the type of Internet address
        given in cgprsCgAlarmHistAddress."
    ::= { cgprsCgAlarmHistEntry 3 }

cgprsCgAlarmHistAddress OBJECT-TYPE
    SYNTAX InetAddress
--    Rsyntax OCTET STRING(SIZE(0..255))
    ACCESS read-only
    STATUS mandatory
    DESCRIPTION
        "The IP address that is used to uniquely identify the CG."
    ::= { cgprsCgAlarmHistEntry 4 }

cgprsCgAlarmHistSeverity OBJECT-TYPE
    SYNTAX CiscoAlarmSeverity
--    Rsyntax INTEGER {
--        cleared(1),
--        indeterminate(2),
--        critical(3),
--        major(4),
--        minor(5),
--        warning(6),
--        info(7)
--        }
    ACCESS read-only
    STATUS mandatory
    DESCRIPTION
        "This object indicates the severity of the alarm."
    ::= { cgprsCgAlarmHistEntry 5 }

cgprsCgAlarmHistInfo OBJECT-TYPE
    SYNTAX SnmpAdminString
--    Rsyntax OCTET STRING(SIZE(0..255))
    ACCESS read-only
    STATUS mandatory
    DESCRIPTION
        "This object provide detailed information when a GPRS  
        charging gateway or charging related alarm is generated."
    ::= { cgprsCgAlarmHistEntry 6 }

cgprsCgAlarmHistLatestIndex OBJECT-TYPE
    SYNTAX Gauge(1..4294967295)
    ACCESS read-only
    STATUS mandatory
    DESCRIPTION
        "The value of cgprsCgAlarmHistIndex for the most recently
        created entry in cgprsCgAlarmHistTable."
    ::= { ciscoGprsChargingAlarms 4 }

cgprsCgAlarmNotif TRAP-TYPE
-- Reverse mappable trap
    ENTERPRISE ciscoGprsCharNotifPrefix
    VARIABLES {
        cgprsCgAlarmHistType, cgprsCgAlarmHistAddrType, 
        cgprsCgAlarmHistAddress, cgprsCgAlarmHistSeverity, 
        cgprsCgAlarmHistInfo }
--  Status
--    mandatory
    DESCRIPTION
        "A cgprsCgAlarmNotif signifies that a GPRS related
        alarm is detected in the managed system.
        This alarm is sent after an entry has been added to 
        cgprsCgAlarmHistTable."
    ::= 1

cgprsCgGatewaySwitchoverNotif TRAP-TYPE
-- Reverse mappable trap
    ENTERPRISE ciscoGprsCharNotifPrefix
    VARIABLES {
        cgprsCgActiveChgGatewayAddrType, 
        cgprsCgActiveChgGatewayAddress, cgprsCgOldChgGatewayAddress }
--  Status
--    mandatory
    DESCRIPTION
        "A notification of this type is generated when the
        charging gateway is switched, the new charging
        gateway is identified by cgprsCgActiveChgGatewayAddress
        and the old charging gateway is identified by
        cgprsCgOldChgGatewayAddress.
        
        The switchover will happen according to the value set
        in cgprsCgGroupSwitchOverTime and the selection of the
        new CG will be according to the value set in
        cgprsCgSwitchOverPriority."
    ::= 2

cgprsCgInServiceModeNotif TRAP-TYPE
-- Reverse mappable trap
    ENTERPRISE ciscoGprsCharNotifPrefix
--  Status
--    mandatory
    DESCRIPTION
        "A notification of this type is generated when the 
        GGSN charging function is in normal mode. This can
        be identified by cgprsCgServiceMode object."
    ::= 3

cgprsCgMaintenanceModeNotif TRAP-TYPE
-- Reverse mappable trap
    ENTERPRISE ciscoGprsCharNotifPrefix
--  Status
--    mandatory
    DESCRIPTION
        "A notification of this type is generated when the 
        GGSN charging function is in maintenance mode. This
        can be identified by cgprsCgServiceMode object."
    ::= 4

cgprsCgMIBConfigGroup OBJECT IDENTIFIER ::= { cgprsCgMIBGroups 1 }
-- OBJECT-GROUP
--  Status
--    obsolete
--  Descr
--    A collection of objects providing charging related  
--    configuration.
--  objects
--    cgprsCgGatewayAddrType, cgprsCgGatewayAddr, 
--    cgprsCgGatewayRowStatus, cgprsCgOperStatus, cgprsCgLinkState, 
--    cgprsCgEnable, cgprsCgCdrLocalSeqNumEnable, 
--    cgprsCgCdrNodeIdEnable, cgprsCgFlowControlEcho, 
--    cgprsCgCdrPktsStatEnable, cgprsCgCdrNonPrimaryEnable, 
--    cgprsCgCdrAggreLimit, cgprsCgTransInterval, cgprsCgPktsQSize, 
--    cgprsCgPathRequest, cgprsCgContainerVolThresh, 
--    cgprsCgMapDataTos, cgprsCgPathProtocol, 
--    cgprsCgServerSwitchTimeout, cgprsCgConditionLimit, 
--    cgprsCgGtpPrimePort, cgprsCgN3BufferSize, 
--    cgprsCgChargeForRoamersOnly, cgprsCgTariffTimeMaxEntries, 
--    cgprsCgTariffTimeNextIndex, cgprsCgTariffTimeRowStatus, 
--    cgprsCgTariffTimeHour, cgprsCgTariffTimeMin, 
--    cgprsCgTariffTimeSec

cgprsCgMIBStatsGroup OBJECT IDENTIFIER ::= { cgprsCgMIBGroups 2 }
-- OBJECT-GROUP
--  Status
--    obsolete
--  Descr
--    A collection of objects providing charging related 
--    statistics.
--  objects
--    cgprsCgDownTimes, cgprsCgAccPtNum, cgprsCgCdrOpenedNum, 
--    cgprsCgCdrClosedNum, cgprsCgContainerNum, 
--    cgprsCgPendingMsgNum, cgprsCgSentMsgNum

cgprsCgMIBAlarmsGroup OBJECT IDENTIFIER ::= { cgprsCgMIBGroups 3 }
-- OBJECT-GROUP
--  Status
--    deprecated
--  Descr
--    A collection of objects providing information about the 
--    charging gateway and charging related alarms.
--    This group is obsoleted by cgprsCgMIBAlarmsGroupRev1.
--  objects
--    cgprsCgAlarmEnable, cgprsCgAlarmHistTableMax, 
--    cgprsCgAlarmHistType, cgprsCgAlarmHistAddrType, 
--    cgprsCgAlarmHistAddress, cgprsCgAlarmHistSeverity, 
--    cgprsCgAlarmHistInfo

cgprsCgMIBConfigGroupRev1 OBJECT IDENTIFIER ::= { cgprsCgMIBGroups 5 }
-- OBJECT-GROUP
--  Status
--    obsolete
--  Descr
--    A collection of objects providing charging related  
--    configuration. This group is deprecated by 
--    cgprsCgMIBConfigGroupRev2.
--  objects
--    cgprsCgGatewayAddrType, cgprsCgGatewayAddr, 
--    cgprsCgGatewayRowStatus, cgprsCgOperStatus, cgprsCgLinkState, 
--    cgprsCgEnable, cgprsCgCdrLocalSeqNumEnable, 
--    cgprsCgCdrNodeIdEnable, cgprsCgFlowControlEcho, 
--    cgprsCgCdrPktsStatEnable, cgprsCgCdrNonPrimaryEnable, 
--    cgprsCgCdrAggreLimit, cgprsCgTransInterval, cgprsCgPktsQSize, 
--    cgprsCgPathRequest, cgprsCgContainerVolThresh, 
--    cgprsCgMapDataTos, cgprsCgPathProtocol, 
--    cgprsCgServerSwitchTimeout, cgprsCgConditionLimit, 
--    cgprsCgGtpPrimePort, cgprsCgN3BufferSize, 
--    cgprsCgChargeForRoamersOnly, cgprsCgTariffTimeMaxEntries, 
--    cgprsCgTariffTimeNextIndex, cgprsCgTariffTimeRowStatus, 
--    cgprsCgTariffTimeHour, cgprsCgTariffTimeMin, 
--    cgprsCgTariffTimeSec, cgprsCgClearCdrPartialCdr, 
--    cgprsCgSgsnChangeLimit

cgprsCgMIBStatsGroupRev1 OBJECT IDENTIFIER ::= { cgprsCgMIBGroups 6 }
-- OBJECT-GROUP
--  Status
--    deprecated
--  Descr
--    A collection of objects providing information about the 
--    charging gateway and charging related alarms.
--  objects
--    cgprsCgDownTimes, cgprsCgAccPtNum, cgprsCgCdrOpenedNum, 
--    cgprsCgCdrClosedNum, cgprsCgContainerNum, 
--    cgprsCgPendingMsgNum, cgprsCgSentMsgNum, 
--    cgprsCgTotalCdrOpened, cgprsCgTotalContainerCreated

cgprsCgMIBConfigGroupRev2 OBJECT IDENTIFIER ::= { cgprsCgMIBGroups 7 }
-- OBJECT-GROUP
--  Status
--    deprecated
--  Descr
--    A collection of objects providing charging related  
--    configuration.
--  objects
--    cgprsCgGatewayAddrType, cgprsCgGatewayAddr, 
--    cgprsCgGatewayRowStatus, cgprsCgOperStatus, cgprsCgLinkState, 
--    cgprsCgEnable, cgprsCgCdrLocalSeqNumEnable, 
--    cgprsCgCdrNodeIdEnable, cgprsCgFlowControlEcho, 
--    cgprsCgCdrPktsStatEnable, cgprsCgCdrAggreLimit, 
--    cgprsCgTransInterval, cgprsCgPktsQSize, cgprsCgPathRequest, 
--    cgprsCgContainerVolThresh, cgprsCgMapDataTos, 
--    cgprsCgPathProtocol, cgprsCgServerSwitchTimeout, 
--    cgprsCgConditionLimit, cgprsCgGtpPrimePort, 
--    cgprsCgN3BufferSize, cgprsCgChargeForRoamersOnly, 
--    cgprsCgTariffTimeMaxEntries, cgprsCgTariffTimeNextIndex, 
--    cgprsCgTariffTimeRowStatus, cgprsCgTariffTimeHour, 
--    cgprsCgTariffTimeMin, cgprsCgTariffTimeSec, 
--    cgprsCgClearCdrPartialCdr, cgprsCgCdrSgsnChangeLimit, 
--    cgprsCgSgsnChangeLimit, cgprsCgRelease, 
--    cgprsCgGtpShortHeaderEnable, cgprsCgTransFormNumRespEnable

cgprsCgMIBAlarmsGroupRev1 OBJECT IDENTIFIER ::= { cgprsCgMIBGroups 8 }
-- OBJECT-GROUP
--  Status
--    mandatory
--  Descr
--    A collection of objects providing information about the
--    charging gateway and charging related alarms.
--  objects
--    cgprsCgAlarmEnable, cgprsCgAlarmHistTableMax, 
--    cgprsCgAlarmHistType, cgprsCgAlarmHistAddrType, 
--    cgprsCgAlarmHistAddress, cgprsCgAlarmHistSeverity, 
--    cgprsCgAlarmHistInfo, cgprsCgAlarmHistLatestIndex

cgprsCgMIBConfigGroupRev3 OBJECT IDENTIFIER ::= { cgprsCgMIBGroups 9 }
-- OBJECT-GROUP
--  Status
--    deprecated
--  Descr
--    A collection of objects providing charging related
--    configuration.
--  objects
--    cgprsCgGatewayAddrType, cgprsCgGatewayAddr, 
--    cgprsCgGatewayRowStatus, cgprsCgOperStatus, cgprsCgLinkState, 
--    cgprsCgEnable, cgprsCgCdrLocalSeqNumEnable, 
--    cgprsCgCdrNodeIdEnable, cgprsCgFlowControlEcho, 
--    cgprsCgCdrPktsStatEnable, cgprsCgCdrAggreLimit, 
--    cgprsCgTransInterval, cgprsCgPktsQSize, cgprsCgPathRequest, 
--    cgprsCgContainerVolThresh, cgprsCgMapDataTos, 
--    cgprsCgPathProtocol, cgprsCgServerSwitchTimeout, 
--    cgprsCgConditionLimit, cgprsCgGtpPrimePort, 
--    cgprsCgN3BufferSize, cgprsCgChargeForRoamersOnly, 
--    cgprsCgTariffTimeMaxEntries, cgprsCgTariffTimeNextIndex, 
--    cgprsCgTariffTimeRowStatus, cgprsCgTariffTimeHour, 
--    cgprsCgTariffTimeMin, cgprsCgTariffTimeSec, 
--    cgprsCgClearCdrPartialCdr, cgprsCgCdrSgsnChangeLimit, 
--    cgprsCgRelease, cgprsCgGtpShortHeaderEnable, 
--    cgprsCgTransFormNumRespEnable, cgprsCgContainerTimeLimit, 
--    cgprsCgProfileRowStatus, cgprsCgProfileDesc, 
--    cgprsCgProfileCategory, cgprsCgProfileCdrSuppress, 
--    cgprsCgProfileVolumeLimit, cgprsCgProfileVolumeLimitReset, 
--    cgprsCgProfileDurLimit, cgprsCgProfileDurLimitReset, 
--    cgprsCgProfileTariffTime, cgprsCgProfileSgsnChange, 
--    cgprsCgProfileMapNum, cgprsCgProfileMapOverride, 
--    cgprsCgProfileMapTrusted, cgprsCgChargingCharReject, 
--    cgprsCgServiceMode, cgprsCgPartialCdrGenEnable, 
--    cgprsCgSwitchOverPriority, cgprsCgCharSelectionMode, 
--    cgprsCgReconnect, cgprsCgPtcEnable, 
--    cgprsCgPtcPossiblyDupEnable

cgprsCgMIBStatsGroupRev2 OBJECT IDENTIFIER ::= { cgprsCgMIBGroups 11 }
-- OBJECT-GROUP
--  Status
--    mandatory
--  Descr
--    A collection of objects providing charging related
--     statistics.
--  objects
--    cgprsCgDownTimes, cgprsCgAccPtNum, cgprsCgCdrOpenedNum, 
--    cgprsCgCdrClosedNum, cgprsCgContainerNum, 
--    cgprsCgPendingMsgNum, cgprsCgSentMsgNum, 
--    cgprsCgTotalCdrOpened, cgprsCgTotalContainerCreated

cgprsCgMIBStatusGroup OBJECT IDENTIFIER ::= { cgprsCgMIBGroups 12 }
-- OBJECT-GROUP
--  Status
--    mandatory
--  Descr
--    A collection of objects providing charging related
--    status.
--  objects
--    cgprsCgActiveChgGatewayAddrType, 
--    cgprsCgActiveChgGatewayAddress, cgprsCgOldChgGatewayAddress

cgprsCgMIBConfigGroupR60 OBJECT IDENTIFIER ::= { cgprsCgMIBGroups 13 }
-- OBJECT-GROUP
--  Status
--    deprecated
--  Descr
--    A collection of objects added as part of GGSN release
--     R6.0.
--  objects
--    cgprsCgCdrOptionServiceRecord, cgprsCgPartialCdrGenEnableAll, 
--    cgprsCgProfileCdrSuppressPrepaid, 
--    cgprsCgProfileContentDccaProfile, 
--    cgprsCgProfileContentPostTime, 
--    cgprsCgProfileContentPostValTime, 
--    cgprsCgProfileContentPostVolume, 
--    cgprsCgProfileContentRulebaseId, cgprsCgCdrOptionApn, 
--    cgprsCgCdrOptionVirtualApn, cgprsCgCdrOptionApnSelMode, 
--    cgprsCgCdrOptionDynamicAddr, cgprsCgCdrOptionNip, 
--    cgprsCgCdrOptionPdpAddress, cgprsCgCdrOptionPdpType, 
--    cgprsCgCdrOptionSerMsisdn, cgprsCgCdrOptionSgsnPlmn, 
--    cgprsCgCdrOptionCamelCharInfo, cgprsCgCdrOptionImeisv, 
--    cgprsCgCdrOptionMsTimeZone, cgprsCgCdrOptionRatType, 
--    cgprsCgCdrOptionUserLocInfo

cgprsCgMIBStatusGroupR60 OBJECT IDENTIFIER ::= { cgprsCgMIBGroups 14 }
-- OBJECT-GROUP
--  Status
--    mandatory
--  Descr
--    A collection of status object added as part of GGSN
--    release R6.0.
--  objects
--    cgprsCgTotalServiceRecords

cgprsCgMIBConfigProfileChangeGroup OBJECT IDENTIFIER ::= { cgprsCgMIBGroups 15 }
-- OBJECT-GROUP
--  Status
--    mandatory
--  Descr
--    A collection of objects providing charging related
--     configuration.
--  objects
--    cgprsCgProfileContentPostQosChange, 
--    cgprsCgProfileContentPostSgsnChange, 
--    cgprsCgProfileContentPostRatChange, 
--    cgprsCgProfileContentPostPlmnChange, 
--    cgprsCgProfileStorageType, cgprsCgServiceRecordIncludeRat, 
--    cgprsCgServiceRecordIncludePlmn

cgprsCgMIBConfigGroupRev4 OBJECT IDENTIFIER ::= { cgprsCgMIBGroups 16 }
-- OBJECT-GROUP
--  Status
--    mandatory
--  Descr
--    A collection of objects providing charging related
--    configurations.
--  objects
--    cgprsCgGatewayAddrType, cgprsCgGatewayAddr, 
--    cgprsCgGatewayRowStatus, cgprsCgOperStatus, cgprsCgLinkState, 
--    cgprsCgEnable, cgprsCgCdrLocalSeqNumEnable, 
--    cgprsCgCdrNodeIdEnable, cgprsCgFlowControlEcho, 
--    cgprsCgCdrPktsStatEnable, cgprsCgCdrAggreLimit, 
--    cgprsCgTransInterval, cgprsCgPktsQSize, cgprsCgPathRequest, 
--    cgprsCgContainerVolThresh, cgprsCgMapDataTos, 
--    cgprsCgPathProtocol, cgprsCgServerSwitchTimeout, 
--    cgprsCgConditionLimit, cgprsCgGtpPrimePort, 
--    cgprsCgN3BufferSize, cgprsCgChargeForRoamersOnly, 
--    cgprsCgTariffTimeMaxEntries, cgprsCgTariffTimeNextIndex, 
--    cgprsCgTariffTimeRowStatus, cgprsCgTariffTimeHour, 
--    cgprsCgTariffTimeMin, cgprsCgTariffTimeSec, 
--    cgprsCgClearCdrPartialCdr, cgprsCgCdrSgsnChangeLimit, 
--    cgprsCgRelease, cgprsCgGtpShortHeaderEnable, 
--    cgprsCgTransFormNumRespEnable, cgprsCgContainerTimeLimit, 
--    cgprsCgProfileRowStatus, cgprsCgProfileDesc, 
--    cgprsCgProfileCategory, cgprsCgProfileCdrSuppress, 
--    cgprsCgProfileVolumeLimit, cgprsCgProfileVolumeLimitReset, 
--    cgprsCgProfileDurLimit, cgprsCgProfileDurLimitReset, 
--    cgprsCgProfileTariffTime, cgprsCgProfileSgsnChange, 
--    cgprsCgProfileMapNumber, cgprsCgProfileMapOverride, 
--    cgprsCgProfileMapTrusted, cgprsCgChargingCharReject, 
--    cgprsCgServiceMode, cgprsCgPartialCdrGenEnable, 
--    cgprsCgSwitchOverPriority, cgprsCgCharSelectionMode, 
--    cgprsCgReconnect, cgprsCgPtcEnable, 
--    cgprsCgPtcPossiblyDupEnable

cgprsCgMIBExtConfigGroup OBJECT IDENTIFIER ::= { cgprsCgMIBGroups 17 }
-- OBJECT-GROUP
--  Status
--    mandatory
--  Descr
--    A collection of status objects.
--  objects
--    cgprsCgCdrOptionServiceRecord, cgprsCgPartialCdrGenEnableAll, 
--    cgprsCgProfileCdrSuppressPrepaid, 
--    cgprsCgProfileContentDccaProfile, 
--    cgprsCgProfileContentPostTime, 
--    cgprsCgProfileContentPostValidityTime, 
--    cgprsCgProfileContentPostVolume, 
--    cgprsCgProfileContentRulebaseId, cgprsCgCdrOptionApn, 
--    cgprsCgCdrOptionVirtualApn, cgprsCgCdrOptionApnSelMode, 
--    cgprsCgCdrOptionDynamicAddr, cgprsCgCdrOptionNip, 
--    cgprsCgCdrOptionPdpAddress, cgprsCgCdrOptionPdpType, 
--    cgprsCgCdrOptionSerMsisdn, cgprsCgCdrOptionSgsnPlmn, 
--    cgprsCgCdrOptionCamelCharInfo, cgprsCgCdrOptionImeisv, 
--    cgprsCgCdrOptionMsTimeZone, cgprsCgCdrOptionRatType, 
--    cgprsCgCdrOptionUserLocInfo

cgprsCgMIBNotifGroup OBJECT IDENTIFIER ::= { cgprsCgMIBGroups 4 }
-- NOTIFICATION-GROUP
--  Status
--    deprecated
--  Descr
--    A collection of notification.
--  notifications
--    cgprsCgAlarmNotif

cgprsCgMIBNotifGroupRev1 OBJECT IDENTIFIER ::= { cgprsCgMIBGroups 10 }
-- NOTIFICATION-GROUP
--  Status
--    mandatory
--  Descr
--    A collection of notification.
--  notifications
--    cgprsCgAlarmNotif, cgprsCgGatewaySwitchoverNotif, 
--    cgprsCgInServiceModeNotif, cgprsCgMaintenanceModeNotif

cgprsCgCompliance OBJECT IDENTIFIER ::= { cgprsCgMIBCompliances 1 }
-- MODULE-COMPLIANCE
--  Status
--    obsolete
--  Descr
--    The compliance statement for entities which implement the 
--    CISCO GPRS CHARGING MIB.
--  Module
--    >>current<<
--   MandGroup
--    cgprsCgMIBConfigGroup
--   OptGroup
--    cgprsCgMIBStatsGroup
--   OptGroup
--    cgprsCgMIBAlarmsGroup
--   OptGroup
--    cgprsCgMIBNotifGroup

cgprsCgComplianceRev1 OBJECT IDENTIFIER ::= { cgprsCgMIBCompliances 2 }
-- MODULE-COMPLIANCE
--  Status
--    obsolete
--  Descr
--    The compliance statement for entities which implement the
--    CISCO GPRS CHARGING MIB. This is deprecated by
--    cgprsCgComplianceRev2.
--  Module
--    >>current<<
--   MandGroup
--    cgprsCgMIBConfigGroupRev1
--   OptGroup
--    cgprsCgMIBStatsGroupRev1
--   OptGroup
--    cgprsCgMIBAlarmsGroup
--   OptGroup
--    cgprsCgMIBNotifGroup

cgprsCgComplianceRev2 OBJECT IDENTIFIER ::= { cgprsCgMIBCompliances 3 }
-- MODULE-COMPLIANCE
--  Status
--    deprecated
--  Descr
--    The compliance statement for entities which implement the
--    CISCO GPRS CHARGING MIB.
--  Module
--    >>current<<
--   MandGroup
--    cgprsCgMIBConfigGroupRev2
--   OptGroup
--    cgprsCgMIBStatsGroupRev1
--   OptGroup
--    cgprsCgMIBAlarmsGroupRev1
--   OptGroup
--    cgprsCgMIBNotifGroup

cgprsCgComplianceRev3 OBJECT IDENTIFIER ::= { cgprsCgMIBCompliances 4 }
-- MODULE-COMPLIANCE
--  Status
--    deprecated
--  Descr
--    The compliance statement for entities which implement the
--    CISCO GPRS CHARGING MIB.
--  Module
--    >>current<<
--   MandGroup
--    cgprsCgMIBConfigGroupRev3
--   OptGroup
--    cgprsCgMIBStatsGroupRev2
--   OptGroup
--    cgprsCgMIBAlarmsGroupRev1
--   OptGroup
--    cgprsCgMIBNotifGroupRev1
--   OptGroup
--    cgprsCgMIBStatusGroup
--   ObjVar
--    cgprsCgProfileRowStatus

cgprsCgComplianceRev4 OBJECT IDENTIFIER ::= { cgprsCgMIBCompliances 5 }
-- MODULE-COMPLIANCE
--  Status
--    deprecated
--  Descr
--    The compliance statement for entities which implement the
--    CISCO GPRS CHARGING MIB.
--  Module
--    >>current<<
--   MandGroup
--    cgprsCgMIBConfigGroupRev3
--   MandGroup
--    cgprsCgMIBStatsGroupRev2
--   MandGroup
--    cgprsCgMIBAlarmsGroupRev1
--   MandGroup
--    cgprsCgMIBNotifGroupRev1
--   MandGroup
--    cgprsCgMIBStatusGroup
--   MandGroup
--    cgprsCgMIBConfigGroupR60
--   MandGroup
--    cgprsCgMIBStatusGroupR60
--   ObjVar
--    cgprsCgProfileRowStatus

cgprsCgComplianceRev5 OBJECT IDENTIFIER ::= { cgprsCgMIBCompliances 6 }
-- MODULE-COMPLIANCE
--  Status
--    deprecated
--  Descr
--    The compliance statement for entities which implement the
--    CISCO GPRS CHARGING MIB.
--  Module
--    >>current<<
--   MandGroup
--    cgprsCgMIBConfigGroupRev3
--   MandGroup
--    cgprsCgMIBStatsGroupRev2
--   MandGroup
--    cgprsCgMIBAlarmsGroupRev1
--   MandGroup
--    cgprsCgMIBNotifGroupRev1
--   MandGroup
--    cgprsCgMIBStatusGroup
--   MandGroup
--    cgprsCgMIBConfigGroupR60
--   MandGroup
--    cgprsCgMIBStatusGroupR60
--   MandGroup
--    cgprsCgMIBConfigProfileChangeGroup
--   ObjVar
--    cgprsCgProfileRowStatus
--   ObjVar
--    cgprsCgProfileStorageType

cgprsCgComplianceRev6 OBJECT IDENTIFIER ::= { cgprsCgMIBCompliances 7 }
-- MODULE-COMPLIANCE
--  Status
--    mandatory
--  Descr
--    The compliance statement for entities which implement the
--    CISCO GPRS CHARGING MIB.
--  Module
--    >>current<<
--   MandGroup
--    cgprsCgMIBConfigGroupRev4
--   MandGroup
--    cgprsCgMIBStatsGroupRev2
--   MandGroup
--    cgprsCgMIBAlarmsGroupRev1
--   MandGroup
--    cgprsCgMIBNotifGroupRev1
--   MandGroup
--    cgprsCgMIBStatusGroup
--   MandGroup
--    cgprsCgMIBStatusGroupR60
--   MandGroup
--    cgprsCgMIBExtConfigGroup
--   MandGroup
--    cgprsCgMIBConfigProfileChangeGroup
--   ObjVar
--    cgprsCgProfileRowStatus
--   ObjVar
--    cgprsCgProfileStorageType


END
