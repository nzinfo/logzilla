-- ********************************************************************
-- CISCO-UNIFIED-COMPUTING-NOTIFS-MIB.my
-- 
-- UCS Fault notifications (traps)
--
-- Copyright (c) 2005-2010 Cisco Systems, Inc. All rights reserved.
-- ********************************************************************

CISCO-UNIFIED-COMPUTING-NOTIFS-MIB DEFINITIONS ::= BEGIN

IMPORTS
        MODULE-IDENTITY,
        NOTIFICATION-TYPE
                FROM SNMPv2-SMI
        ciscoUnifiedComputingMIB
            FROM CISCO-UNIFIED-COMPUTING-MIB
        cucsFaultDescription,
        cucsFaultAffectedObjectId,
        cucsFaultAffectedObjectDn,
        cucsFaultCreationTime,
        cucsFaultLastModificationTime,
        cucsFaultCode,
        cucsFaultType,
        cucsFaultProbableCause,
        cucsFaultSeverity,
        cucsFaultOccur,
        cucsFaultId
            FROM CISCO-UNIFIED-COMPUTING-FAULT-MIB;

ciscoUnifiedComputingMIBNotifs MODULE-IDENTITY
        LAST-UPDATED  "201001290000Z" 
        ORGANIZATION  "Cisco"
        CONTACT-INFO
            "Cisco Systems
            Customer Service

            Postal: 170 West Tasman Drive
            San Jose, CA  95134
            USA

            Tel: +1 800 553-NETS

            E-mail: savbu-snmp-dev@cisco.com"
      DESCRIPTION
         "Fault traps (notifications) issued by the UCS system"
      REVISION "201001290000Z" 
      DESCRIPTION
         "Initial version of this MIB module."
   ::= { ciscoUnifiedComputingMIB 0 }

cucsFaultActiveNotif NOTIFICATION-TYPE
      OBJECTS  {
                cucsFaultDescription,
                cucsFaultAffectedObjectId,
                cucsFaultAffectedObjectDn,
                cucsFaultCreationTime,
                cucsFaultLastModificationTime,
                cucsFaultCode,
                cucsFaultType,
                cucsFaultProbableCause,
                cucsFaultSeverity,
                cucsFaultOccur,
                cucsFaultId
               }
      STATUS current
      DESCRIPTION
          "This notification is generated by a UCS node whenever a fault
          is active and the fault state changes."
      ::= { ciscoUnifiedComputingMIBNotifs 1 }

cucsFaultClearNotif NOTIFICATION-TYPE
      OBJECTS  {
                cucsFaultDescription,
                cucsFaultAffectedObjectId,
                cucsFaultAffectedObjectDn,
                cucsFaultCreationTime,
                cucsFaultLastModificationTime,
                cucsFaultCode,
                cucsFaultType,
                cucsFaultProbableCause,
                cucsFaultSeverity,
                cucsFaultOccur,
                cucsFaultId
               }
      STATUS current
      DESCRIPTION
          "This notification is generated by a UCS node whenever a fault
          is cleared."
      ::= { ciscoUnifiedComputingMIBNotifs 2 }

END
