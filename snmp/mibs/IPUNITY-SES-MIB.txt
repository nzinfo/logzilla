--
-- $Id: IPUNITY-SES.mib,v 1.9.4.3 2007/10/25 09:40:45 himadrisaha Exp $
--

IPUNITY-SES-MIB DEFINITIONS ::= BEGIN

IMPORTS
    MODULE-IDENTITY, OBJECT-TYPE, NOTIFICATION-TYPE, Integer32, TimeTicks, Counter64,
    enterprises
        FROM SNMPv2-SMI
    DisplayString, DateAndTime
        FROM SNMPv2-TC
    applIndex
        FROM NETWORK-SERVICES-MIB;

ipunity OBJECT IDENTIFIER ::= { enterprises 5134 }

appserver MODULE-IDENTITY
    LAST-UPDATED "200508150000Z"  -- Aug 15th 2005
    ORGANIZATION "IP Unity"
    CONTACT-INFO
         "Prasada R Vankayalapati
          IP Unity
          475 Sycamore Dr
          Milpitas CA  95035
          USA

          Tel: +1 408 582-1100
          E-mail: support@ipunity.com"
    DESCRIPTION
	     "IP Unity Harmony Application Server MIB."
    ::= { ipunity 2 }

--
-- Groups defined for appserver MIB
--

framework       OBJECT IDENTIFIER ::= { appserver 1 }
umApp           OBJECT IDENTIFIER ::= { appserver 2 }
confApp         OBJECT IDENTIFIER ::= { appserver 3 }

asSys           OBJECT IDENTIFIER ::= { framework 1 }
asStatsScalars  OBJECT IDENTIFIER ::= { framework 2 }
asStatsTables   OBJECT IDENTIFIER ::= { framework 3 }
ipuSIP          OBJECT IDENTIFIER ::= { framework 4 }
ipuMGCPScalars  OBJECT IDENTIFIER ::= { framework 5 }
ipuMGCPTables   OBJECT IDENTIFIER ::= { framework 6 }
frameConfig     OBJECT IDENTIFIER ::= { framework 7 }
asSysTables	OBJECT IDENTIFIER ::= { framework 8 }

umScalars       OBJECT IDENTIFIER ::= { umApp 1 }
umTables        OBJECT IDENTIFIER ::= { umApp 2 }
paging          OBJECT IDENTIFIER ::= { umApp 3 }
msgWait         OBJECT IDENTIFIER ::= { umApp 4 }
notification    OBJECT IDENTIFIER ::= { umApp 5 } 

confScalars     OBJECT IDENTIFIER ::= { confApp 1 }
confTables      OBJECT IDENTIFIER ::= { confApp 2 }

asNotifications OBJECT IDENTIFIER ::= { appserver 10 }

--
-- Object definitions
--

asSysDescr OBJECT-TYPE
    SYNTAX      DisplayString (SIZE (0..255))
    MAX-ACCESS  read-only
    STATUS      current
    DESCRIPTION
        "Description of the App server. Gives version of the software 
        as well."
    ::= { asSys 1 }

asSysObjectID OBJECT-TYPE
    SYNTAX      OBJECT IDENTIFIER
    MAX-ACCESS  read-only
    STATUS      current
    DESCRIPTION
        "Authoritative identification of the app server. Object Identifier
         that Identifies this entity as IP Unity App Server. Its value is
         1.3.6.1.4.1.5134.2"
    ::= { asSys 2 }

asSysUptime OBJECT-TYPE
    SYNTAX      TimeTicks
    MAX-ACCESS  read-only
    STATUS      current
    DESCRIPTION
        "Uptime of the Application Server. The time (in hundredths of a second) 
         since the network management portion of the system was last 
         re-initialized."
    ::= { asSys 3 }

asMode OBJECT-TYPE
    SYNTAX      INTEGER {
                    active (1),
                    stand-by (2)
                }
    MAX-ACCESS  read-only
    STATUS      obsolete
    DESCRIPTION
        "This object gives the mode of operation of the app server."
    ::= { asSys 4 }

asProcessName OBJECT-TYPE
    SYNTAX      DisplayString (SIZE (0..20))
    MAX-ACCESS  accessible-for-notify
    STATUS      current
    DESCRIPTION
        "This object gives the Name of the Process."
    ::= { asSys 5 }

asProcessState OBJECT-TYPE
    SYNTAX      INTEGER {
                    running (1),
                    stopped (2),
                    restarted (3),
                    unableToRestart (4),
                    notResponding (5)
                }
    MAX-ACCESS  accessible-for-notify
    STATUS      current
    DESCRIPTION
        "This object gives the State of the Process"
    ::= { asSys 6 }

asTrapInfoString OBJECT-TYPE
    SYNTAX      DisplayString (SIZE (0..255))
    MAX-ACCESS  accessible-for-notify
    STATUS      current
    DESCRIPTION
        "The optional textual description associated with any of the 
	 proprietary traps defined in the Application Server MIB."
    ::= { asSys 7 }

asTrapSeverity OBJECT-TYPE
    SYNTAX      INTEGER {
		    clear (1),
		    informational (2),
		    warning (3),
		    minor (4),
		    major (5),
		    critical (6)
		}
    MAX-ACCESS  accessible-for-notify
    STATUS      current
    DESCRIPTION
        "Gives the severity of the trap message generated by the 
         Application Server. Every trap message contains this object
	 as first object in its variable bindings."
    ::= { asSys 8 }

asStatsCallsWithNoApp OBJECT-TYPE
    SYNTAX      Counter32
    MAX-ACCESS  read-only
    STATUS      current
    DESCRIPTION
        "The number of calls that could not be mapped to any
        application."
    ::= { asStatsScalars 1 }

asSIPStatsReset OBJECT-TYPE
    SYNTAX      INTEGER {
                   none (0),
                   reset (1)
                }
    MAX-ACCESS  read-write
    STATUS      current
    DESCRIPTION
        "This variable is used to reset all the SIP statistics. Manager
         should set value as 1 to reset the SIP statistics." 
    ::= { asStatsScalars 2 }

asMGCPStatsReset OBJECT-TYPE
    SYNTAX      INTEGER {
                   none (0),
                   reset (1)
                }
    MAX-ACCESS  read-write
    STATUS      current
    DESCRIPTION
        "This variable is used to reset all the MGCP statistics. Manager
         should set value as 1 to reset the MGCP statistics." 
    ::= { asStatsScalars 3 }

asCallStatsTable OBJECT-TYPE
    SYNTAX     SEQUENCE OF AsCallStatsEntry   
    MAX-ACCESS not-accessible   
    STATUS     current   
    DESCRIPTION   
         "This table contains the Call statistics for each application
          that is supported by Application Server." 
    ::= { asStatsTables 1 }   
   
asCallStatsEntry OBJECT-TYPE   
    SYNTAX     AsCallStatsEntry
    MAX-ACCESS not-accessible   
    STATUS     current   
    DESCRIPTION   
         "A row of Call statistics per application (Ex conf, UM etc.,). 

          asAppIndex is used to uniquely identify application and asAppName
          gives the application name. "
    INDEX { asAppIndex }   
    ::= { asCallStatsTable 1}

AsCallStatsEntry ::=   
    SEQUENCE {  
          asAppIndex                          Integer32,
          asAppName                           DisplayString,
          asAppAdminStatus                    INTEGER,
          asAppOperStatus                     INTEGER,
          asInCallsInProgress                 Gauge32,
          asInCallsCompleted                  Counter32,
          asInCallsFwRejected                 Counter32,
          asInCallsAppRejected                Counter32,
          asInCallSetupAttempts               Counter32,
          asInCallSetupSuccess                Counter32,
          asInCallSetupMsFailures             Counter32,
          asInCallSetupCaFailures             Counter32,
          asInCallTeardownMsAttempts          Counter32,
          asInCallTeardownCaAttempts          Counter32,
          asInCallTeardownAppAttempts         Counter32,
          asInCallTeardownFwAttempts          Counter32,
          asInCallTeardownMsFailures          Counter32,
          asInCallTeardownCaFailures          Counter32,
          asOutCallsInProgress                Gauge32,
          asOutCallsCompleted                 Counter32,
          asOutCallsFwCancelled               Counter32,
          asOutCallsAppCancelled              Counter32,
          asOutCallSetupAttempts              Counter32,
          asOutCallSetupSuccess               Counter32,
          asOutCallSetupMsFailures            Counter32,
          asOutCallSetupCaFailures            Counter32,
          asOutCallTeardownMsAttempts         Counter32,
          asOutCallTeardownCaAttempts         Counter32,
          asOutCallTeardownAppAttempts        Counter32,
          asOutCallTeardownFwAttempts         Counter32,
          asOutCallTeardownMsFailures         Counter32,
          asOutCallTeardownCaFailures         Counter32,
          asHungCallsDropped                  Counter32,
	  asCallStatsReset		      INTEGER,
          asCallTransfersAttempted            Counter32,
          asCallTransfersSuccess              Counter32,
          asCallTransfersFailedOnApp          Counter32,
          asCallTransfersFailedOnCa           Counter32,
          asInCallsRedirected                 Counter32,
          asInCallsNotRespondedByFramework    Counter32,
          asInCallsTearedDownSessionTimer     Counter32,
          asOutCallsTearedDownSessionTimer    Counter32

    } 

asAppIndex OBJECT-TYPE
    SYNTAX      Integer32 (1..100)
    MAX-ACCESS  not-accessible
    STATUS      current
    DESCRIPTION
        "App server Application Index."
    ::= { asCallStatsEntry 1 }

asAppName OBJECT-TYPE
    SYNTAX      DisplayString (SIZE (0..20))
    MAX-ACCESS  read-only
    STATUS      current
    DESCRIPTION
        "Name of the Application."
    ::= { asCallStatsEntry 2 }

asAppAdminStatus OBJECT-TYPE
    SYNTAX      INTEGER {
                    up (1),
                    down (2)
                }
    MAX-ACCESS  read-write
    STATUS      current
    DESCRIPTION
        "The desired state of this Application."
    ::= { asCallStatsEntry 3 }

asAppOperStatus OBJECT-TYPE
    SYNTAX      INTEGER {
                    up (1),
                    down (2)
                }
    MAX-ACCESS  read-only
    STATUS      current
    DESCRIPTION
        "The operational status of the Application."
    ::= { asCallStatsEntry 4 }

asInCallsInProgress OBJECT-TYPE
    SYNTAX      Gauge32
    MAX-ACCESS  read-only
    STATUS      current
    DESCRIPTION
        "The number of active In-Calls."
    ::= { asCallStatsEntry 5 }

asInCallsCompleted OBJECT-TYPE
    SYNTAX      Counter32
    MAX-ACCESS  read-only
    STATUS      current
    DESCRIPTION
        "The number of completed In-Calls since startup."
    ::= { asCallStatsEntry 6 }

asInCallsFwRejected OBJECT-TYPE
    SYNTAX      Counter32
    MAX-ACCESS  read-only
    STATUS      current
    DESCRIPTION
        "The number of In-Calls rejected by Framework."
    ::= { asCallStatsEntry 7 }

asInCallsAppRejected OBJECT-TYPE
    SYNTAX      Counter32
    MAX-ACCESS  read-only
    STATUS      current
    DESCRIPTION
        "The number of In-Calls rejected by Application."
    ::= { asCallStatsEntry 8 }

asInCallSetupAttempts OBJECT-TYPE
    SYNTAX      Counter32
    MAX-ACCESS  read-only
    STATUS      current
    DESCRIPTION
        "Number of In-Call setup attempts."
    ::= { asCallStatsEntry 9 }

asInCallSetupSuccess OBJECT-TYPE
    SYNTAX      Counter32
    MAX-ACCESS  read-only
    STATUS      current
    DESCRIPTION
        "Number of In-Call setups that are success."
    ::= { asCallStatsEntry 10 }

asInCallSetupMsFailures OBJECT-TYPE
    SYNTAX      Counter32
    MAX-ACCESS  read-only
    STATUS      current
    DESCRIPTION
        "Number of In-Call setup Failures due to resource allocation 
         failure."
    ::= { asCallStatsEntry 11 }

asInCallSetupCaFailures OBJECT-TYPE
    SYNTAX      Counter32
    MAX-ACCESS  read-only
    STATUS      current
    DESCRIPTION
        "Number of In-Call setup Failures."
    ::= { asCallStatsEntry 12 }

asInCallTeardownMsAttempts OBJECT-TYPE
    SYNTAX      Counter32
    MAX-ACCESS  read-only
    STATUS      current
    DESCRIPTION
        "Number of In-Call teardown attempts by Media server."
    ::= { asCallStatsEntry 13 }

asInCallTeardownCaAttempts OBJECT-TYPE
    SYNTAX      Counter32
    MAX-ACCESS  read-only
    STATUS      current
    DESCRIPTION
        "Number of In-Call teardown attempts by Call Agent."
    ::= { asCallStatsEntry 14 }

asInCallTeardownAppAttempts OBJECT-TYPE
    SYNTAX      Counter32
    MAX-ACCESS  read-only
    STATUS      current
    DESCRIPTION
        "Number of In-Call teardown attempts by the Application."
    ::= { asCallStatsEntry 15 }

asInCallTeardownFwAttempts OBJECT-TYPE
    SYNTAX      Counter32
    MAX-ACCESS  read-only
    STATUS      current
    DESCRIPTION
        "Number of In-Call teardown attempts by Framework."
    ::= { asCallStatsEntry 16 }

asInCallTeardownMsFailures OBJECT-TYPE
    SYNTAX      Counter32
    MAX-ACCESS  read-only
    STATUS      current
    DESCRIPTION
        "Number of In-Call teardown Failures."
    ::= { asCallStatsEntry 17 }

asInCallTeardownCaFailures OBJECT-TYPE
    SYNTAX      Counter32
    MAX-ACCESS  read-only
    STATUS      current
    DESCRIPTION
        "Number of In-Call teardown Failures."
    ::= { asCallStatsEntry 18 }

asOutCallsInProgress OBJECT-TYPE
    SYNTAX      Gauge32
    MAX-ACCESS  read-only
    STATUS      current
    DESCRIPTION
        "The number of active Out-Calls."
    ::= { asCallStatsEntry 19 }

asOutCallsCompleted OBJECT-TYPE
    SYNTAX      Counter32
    MAX-ACCESS  read-only
    STATUS      current
    DESCRIPTION
        "The number of completed Out-Calls since startup."
    ::= { asCallStatsEntry 20 }

asOutCallsFwCancelled OBJECT-TYPE
    SYNTAX      Counter32
    MAX-ACCESS  read-only
    STATUS      current
    DESCRIPTION
        "The number of Out-Calls Cancelled by Framework."
    ::= { asCallStatsEntry 21 }

asOutCallsAppCancelled OBJECT-TYPE
    SYNTAX      Counter32
    MAX-ACCESS  read-only
    STATUS      current
    DESCRIPTION
        "The number of Out-Calls Cancelled by Application."
    ::= { asCallStatsEntry 22 }

asOutCallSetupAttempts OBJECT-TYPE
    SYNTAX      Counter32
    MAX-ACCESS  read-only
    STATUS      current
    DESCRIPTION
        "Number of Out-Call setup attempts."
    ::= { asCallStatsEntry 23 }

asOutCallSetupSuccess OBJECT-TYPE
    SYNTAX      Counter32
    MAX-ACCESS  read-only
    STATUS      current
    DESCRIPTION
        "Number of Out-Call setups that are success."
    ::= { asCallStatsEntry 24 }

asOutCallSetupMsFailures OBJECT-TYPE
    SYNTAX      Counter32
    MAX-ACCESS  read-only
    STATUS      current
    DESCRIPTION
        "Number of Out-Call setup Failures due to resource allocation 
         failure."
    ::= { asCallStatsEntry 25 }

asOutCallSetupCaFailures OBJECT-TYPE
    SYNTAX      Counter32
    MAX-ACCESS  read-only
    STATUS      current
    DESCRIPTION
        "Number of Out-Call setup Failures."
    ::= { asCallStatsEntry 26 }

asOutCallTeardownMsAttempts OBJECT-TYPE
    SYNTAX      Counter32
    MAX-ACCESS  read-only
    STATUS      current
    DESCRIPTION
        "Number of Out-Call teardown attempts by Media server."
    ::= { asCallStatsEntry 27 }

asOutCallTeardownCaAttempts OBJECT-TYPE
    SYNTAX      Counter32
    MAX-ACCESS  read-only
    STATUS      current
    DESCRIPTION
        "Number of Out-Call teardown attempts by Call Agent."
    ::= { asCallStatsEntry 28 }

asOutCallTeardownAppAttempts OBJECT-TYPE
    SYNTAX      Counter32
    MAX-ACCESS  read-only
    STATUS      current
    DESCRIPTION
        "Number of Out-Call teardown attempts by the Application."
    ::= { asCallStatsEntry 29 }

asOutCallTeardownFwAttempts OBJECT-TYPE
    SYNTAX      Counter32
    MAX-ACCESS  read-only
    STATUS      current
    DESCRIPTION
        "Number of Out-Call teardown attempts by Framework."
    ::= { asCallStatsEntry 30 }

asOutCallTeardownMsFailures OBJECT-TYPE
    SYNTAX      Counter32
    MAX-ACCESS  read-only
    STATUS      current
    DESCRIPTION
        "Number of Out-Call teardown Failures."
    ::= { asCallStatsEntry 31 }

asOutCallTeardownCaFailures OBJECT-TYPE
    SYNTAX      Counter32
    MAX-ACCESS  read-only
    STATUS      current
    DESCRIPTION
        "Number of Out-Call teardown Failures."
    ::= { asCallStatsEntry 32 }

asHungCallsDropped OBJECT-TYPE
    SYNTAX      Counter32
    MAX-ACCESS  read-only
    STATUS      current
    DESCRIPTION
        "Number of Hung calls that are dropped."
    ::= { asCallStatsEntry 33 }

asCallStatsReset OBJECT-TYPE
    SYNTAX      INTEGER {
                    none (0),
                    reset (1) 
                }
    MAX-ACCESS  read-write
    STATUS      current
    DESCRIPTION
        "This variable is used to reset the call stats for the application on this node. Manager
         should set value as 1 to reset the call stats for the application. 
         If Manager wants to reset call stats for all the node in the cluster then it should
         send SET request to all the nodes seperately."
    ::= { asCallStatsEntry 34 }

asCallTransfersAttempted OBJECT-TYPE
    SYNTAX      Counter32
    MAX-ACCESS  read-only
    STATUS      current
    DESCRIPTION
        "Number of attempted call transfers."
    ::= { asCallStatsEntry 35 }

asCallTransfersSuccess OBJECT-TYPE
    SYNTAX      Counter32
    MAX-ACCESS  read-only
    STATUS      current
    DESCRIPTION
        "Number of call transfers that are successfull."
    ::= { asCallStatsEntry 36 }

asCallTransfersFailedOnApp OBJECT-TYPE
    SYNTAX      Counter32
    MAX-ACCESS  read-only
    STATUS      current
    DESCRIPTION
        "Number of call transfers failed on Application."
    ::= { asCallStatsEntry 37 }

asCallTransfersFailedOnCa OBJECT-TYPE
    SYNTAX      Counter32
    MAX-ACCESS  read-only
    STATUS      current
    DESCRIPTION
        "Number of attempted call transfers failed on Call Agent."
    ::= { asCallStatsEntry 38 }

asInCallsRedirected OBJECT-TYPE
    SYNTAX      Counter32
    MAX-ACCESS  read-only
    STATUS      current
    DESCRIPTION
        "Number of calls that framework has redirected to another node in the cluster."
    ::= { asCallStatsEntry 39 }

asInCallsNotRespondedByFramework OBJECT-TYPE
    SYNTAX      Counter32
    MAX-ACCESS  read-only
    STATUS      current
    DESCRIPTION
        "Number of calls for which framework did not respond bcos it was locked."
    ::= { asCallStatsEntry 40 }

asInCallsTearedDownSessionTimer OBJECT-TYPE
    SYNTAX      Counter32
    MAX-ACCESS  read-only
    STATUS      current
    DESCRIPTION
        "Number of in calls teared down because of the session timer expiration."
    ::= { asCallStatsEntry 41 }

asOutCallsTearedDownSessionTimer OBJECT-TYPE
    SYNTAX      Counter32
    MAX-ACCESS  read-only
    STATUS      current
    DESCRIPTION
        "Number of out calls teared down because of the session timer expiration."
    ::= { asCallStatsEntry 42 }

asClusterCallStatsTable OBJECT-TYPE
    SYNTAX     SEQUENCE OF AsClusterCallStatsEntry   
    MAX-ACCESS not-accessible   
    STATUS     current   
    DESCRIPTION   
         "This table contains the Call statistics for each application
          that is supported by Application Server cluster. This table is 
          present only in HA environment and reported by the captain node." 
    ::= { asStatsTables 2 }   
   
asClusterCallStatsEntry OBJECT-TYPE   
    SYNTAX     AsClusterCallStatsEntry
    MAX-ACCESS not-accessible   
    STATUS     current   
    DESCRIPTION   
         "A row of Call statistics per application (Ex conf, UM etc.,). 
          asAppIndex uniquely identifies the application and asAppName
          in asCallStatsTable gives the application name. "
    INDEX { asAppIndex }   
    ::= { asClusterCallStatsTable 1}

AsClusterCallStatsEntry ::=   
    SEQUENCE {  
          asClusterInCallsInProgress                 Gauge32,
          asClusterInCallsCompleted                  Counter64,
          asClusterInCallsFwRejected                 Counter64,
          asClusterInCallsAppRejected                Counter64,
          asClusterInCallSetupAttempts               Counter64,
          asClusterInCallSetupSuccess                Counter64,
          asClusterInCallSetupMsFailures             Counter64,
          asClusterInCallSetupCaFailures             Counter64,
          asClusterInCallTeardownMsAttempts          Counter64,
          asClusterInCallTeardownCaAttempts          Counter64,
          asClusterInCallTeardownAppAttempts         Counter64,
          asClusterInCallTeardownFwAttempts          Counter64,
          asClusterInCallTeardownMsFailures          Counter64,
          asClusterInCallTeardownCaFailures          Counter64,
          asClusterOutCallsInProgress                Gauge32,
          asClusterOutCallsCompleted                 Counter64,
          asClusterOutCallsFwCancelled               Counter64,
          asClusterOutCallsAppCancelled              Counter64,
          asClusterOutCallSetupAttempts              Counter64,
          asClusterOutCallSetupSuccess               Counter64,
          asClusterOutCallSetupMsFailures            Counter64,
          asClusterOutCallSetupCaFailures            Counter64,
          asClusterOutCallTeardownMsAttempts         Counter64,
          asClusterOutCallTeardownCaAttempts         Counter64,
          asClusterOutCallTeardownAppAttempts        Counter64,
          asClusterOutCallTeardownFwAttempts         Counter64,
          asClusterOutCallTeardownMsFailures         Counter64,
          asClusterOutCallTeardownCaFailures         Counter64,
          asClusterHungCallsDropped                  Counter64,
          asClusterStatsReset                        INTEGER,
          asClusterCallTransfersAttempted            Counter64,
          asClusterCallTransfersSuccess              Counter64,
          asClusterCallTransfersFailedOnApp          Counter64,
          asClusterCallTransfersFailedOnCa           Counter64
    } 

asClusterInCallsInProgress OBJECT-TYPE
    SYNTAX      Gauge32
    MAX-ACCESS  read-only
    STATUS      current
    DESCRIPTION
        "The number of active In-Calls."
    ::= { asClusterCallStatsEntry 1 }

asClusterInCallsCompleted OBJECT-TYPE
    SYNTAX      Counter64
    MAX-ACCESS  read-only
    STATUS      current
    DESCRIPTION
        "The number of completed In-Calls since startup."
    ::= { asClusterCallStatsEntry 2 }

asClusterInCallsFwRejected OBJECT-TYPE
    SYNTAX      Counter64
    MAX-ACCESS  read-only
    STATUS      current
    DESCRIPTION
        "The number of In-Calls rejected by Framework."
    ::= { asClusterCallStatsEntry 3 }

asClusterInCallsAppRejected OBJECT-TYPE
    SYNTAX      Counter64
    MAX-ACCESS  read-only
    STATUS      current
    DESCRIPTION
        "The number of In-Calls rejected by Application."
    ::= { asClusterCallStatsEntry 4 }

asClusterInCallSetupAttempts OBJECT-TYPE
    SYNTAX      Counter64
    MAX-ACCESS  read-only
    STATUS      current
    DESCRIPTION
        "Number of In-Call setup attempts."
    ::= { asClusterCallStatsEntry 5 }

asClusterInCallSetupSuccess OBJECT-TYPE
    SYNTAX      Counter64
    MAX-ACCESS  read-only
    STATUS      current
    DESCRIPTION
        "Number of In-Call setups that are success."
    ::= { asClusterCallStatsEntry 6 }

asClusterInCallSetupMsFailures OBJECT-TYPE
    SYNTAX      Counter64
    MAX-ACCESS  read-only
    STATUS      current
    DESCRIPTION
        "Number of In-Call setup Failures due to resource allocation 
         failure."
    ::= { asClusterCallStatsEntry 7 }

asClusterInCallSetupCaFailures OBJECT-TYPE
    SYNTAX      Counter64
    MAX-ACCESS  read-only
    STATUS      current
    DESCRIPTION
        "Number of In-Call setup Failures."
    ::= { asClusterCallStatsEntry 8 }

asClusterInCallTeardownMsAttempts OBJECT-TYPE
    SYNTAX      Counter64
    MAX-ACCESS  read-only
    STATUS      current
    DESCRIPTION
        "Number of In-Call teardown attempts by Media server."
    ::= { asClusterCallStatsEntry 9 }

asClusterInCallTeardownCaAttempts OBJECT-TYPE
    SYNTAX      Counter64
    MAX-ACCESS  read-only
    STATUS      current
    DESCRIPTION
        "Number of In-Call teardown attempts by Call Agent."
    ::= { asClusterCallStatsEntry 10 }

asClusterInCallTeardownAppAttempts OBJECT-TYPE
    SYNTAX      Counter64
    MAX-ACCESS  read-only
    STATUS      current
    DESCRIPTION
        "Number of In-Call teardown attempts by the Application."
    ::= { asClusterCallStatsEntry 11 }

asClusterInCallTeardownFwAttempts OBJECT-TYPE
    SYNTAX      Counter64
    MAX-ACCESS  read-only
    STATUS      current
    DESCRIPTION
        "Number of In-Call teardown attempts by Framework."
    ::= { asClusterCallStatsEntry 12 }

asClusterInCallTeardownMsFailures OBJECT-TYPE
    SYNTAX      Counter64
    MAX-ACCESS  read-only
    STATUS      current
    DESCRIPTION
        "Number of In-Call teardown Failures."
    ::= { asClusterCallStatsEntry 13 }

asClusterInCallTeardownCaFailures OBJECT-TYPE
    SYNTAX      Counter64
    MAX-ACCESS  read-only
    STATUS      current
    DESCRIPTION
        "Number of In-Call teardown Failures."
    ::= { asClusterCallStatsEntry 14 }

asClusterOutCallsInProgress OBJECT-TYPE
    SYNTAX      Gauge32
    MAX-ACCESS  read-only
    STATUS      current
    DESCRIPTION
        "The number of active Out-Calls."
    ::= { asClusterCallStatsEntry 15 }

asClusterOutCallsCompleted OBJECT-TYPE
    SYNTAX      Counter64
    MAX-ACCESS  read-only
    STATUS      current
    DESCRIPTION
        "The number of completed Out-Calls since startup."
    ::= { asClusterCallStatsEntry 16 }

asClusterOutCallsFwCancelled OBJECT-TYPE
    SYNTAX      Counter64
    MAX-ACCESS  read-only
    STATUS      current
    DESCRIPTION
        "The number of Out-Calls Cancelled by Framework."
    ::= { asClusterCallStatsEntry 17 }

asClusterOutCallsAppCancelled OBJECT-TYPE
    SYNTAX      Counter64
    MAX-ACCESS  read-only
    STATUS      current
    DESCRIPTION
        "The number of Out-Calls Cancelled by Application."
    ::= { asClusterCallStatsEntry 18 }

asClusterOutCallSetupAttempts OBJECT-TYPE
    SYNTAX      Counter64
    MAX-ACCESS  read-only
    STATUS      current
    DESCRIPTION
        "Number of Out-Call setup attempts."
    ::= { asClusterCallStatsEntry 19 }

asClusterOutCallSetupSuccess OBJECT-TYPE
    SYNTAX      Counter64
    MAX-ACCESS  read-only
    STATUS      current
    DESCRIPTION
        "Number of Out-Call setups that are success."
    ::= { asClusterCallStatsEntry 20 }

asClusterOutCallSetupMsFailures OBJECT-TYPE
    SYNTAX      Counter64
    MAX-ACCESS  read-only
    STATUS      current
    DESCRIPTION
        "Number of Out-Call setup Failures due to resource allocation 
         failure."
    ::= { asClusterCallStatsEntry 21 }

asClusterOutCallSetupCaFailures OBJECT-TYPE
    SYNTAX      Counter64
    MAX-ACCESS  read-only
    STATUS      current
    DESCRIPTION
        "Number of Out-Call setup Failures."
    ::= { asClusterCallStatsEntry 22 }

asClusterOutCallTeardownMsAttempts OBJECT-TYPE
    SYNTAX      Counter64
    MAX-ACCESS  read-only
    STATUS      current
    DESCRIPTION
        "Number of Out-Call teardown attempts by Media server."
    ::= { asClusterCallStatsEntry 23 }

asClusterOutCallTeardownCaAttempts OBJECT-TYPE
    SYNTAX      Counter64
    MAX-ACCESS  read-only
    STATUS      current
    DESCRIPTION
        "Number of Out-Call teardown attempts by Call Agent."
    ::= { asClusterCallStatsEntry 24 }

asClusterOutCallTeardownAppAttempts OBJECT-TYPE
    SYNTAX      Counter64
    MAX-ACCESS  read-only
    STATUS      current
    DESCRIPTION
        "Number of Out-Call teardown attempts by the Application."
    ::= { asClusterCallStatsEntry 25 }

asClusterOutCallTeardownFwAttempts OBJECT-TYPE
    SYNTAX      Counter64
    MAX-ACCESS  read-only
    STATUS      current
    DESCRIPTION
        "Number of Out-Call teardown attempts by Framework."
    ::= { asClusterCallStatsEntry 26 }

asClusterOutCallTeardownMsFailures OBJECT-TYPE
    SYNTAX      Counter64
    MAX-ACCESS  read-only
    STATUS      current
    DESCRIPTION
        "Number of Out-Call teardown Failures."
    ::= { asClusterCallStatsEntry 27 }

asClusterOutCallTeardownCaFailures OBJECT-TYPE
    SYNTAX      Counter64
    MAX-ACCESS  read-only
    STATUS      current
    DESCRIPTION
        "Number of Out-Call teardown Failures."
    ::= { asClusterCallStatsEntry 28 }

asClusterHungCallsDropped OBJECT-TYPE
    SYNTAX      Counter64
    MAX-ACCESS  read-only
    STATUS      current
    DESCRIPTION
        "Number of Hung calls that are dropped."
    ::= { asClusterCallStatsEntry 29 }

asClusterStatsReset OBJECT-TYPE
    SYNTAX      INTEGER {
                    none (0),
                    reset (1) 
                }
    MAX-ACCESS  read-write
    STATUS      current
    DESCRIPTION
        "This variable is used to reset the cluster stats for the application. Manager
         should set value as 1 to reset the cluster stats for the application. Only the
         captain node can reset the cluster statistics."
    ::= { asClusterCallStatsEntry 30 }

asClusterCallTransfersAttempted OBJECT-TYPE
    SYNTAX      Counter64
    MAX-ACCESS  read-only
    STATUS      current
    DESCRIPTION
        "Number of attempted call transfers on this cluster."
    ::= { asClusterCallStatsEntry 31 }

asClusterCallTransfersSuccess OBJECT-TYPE
    SYNTAX      Counter64
    MAX-ACCESS  read-only
    STATUS      current
    DESCRIPTION
        "Number of call transfers that are successfull."
    ::= { asClusterCallStatsEntry 32 }

asClusterCallTransfersFailedOnApp OBJECT-TYPE
    SYNTAX      Counter64
    MAX-ACCESS  read-only
    STATUS      current
    DESCRIPTION
        "Number of call transfers failed on Application."
    ::= { asClusterCallStatsEntry 33 }

asClusterCallTransfersFailedOnCa OBJECT-TYPE
    SYNTAX      Counter64
    MAX-ACCESS  read-only
    STATUS      current
    DESCRIPTION
        "Number of attempted call transfers failed on Call Agent."
    ::= { asClusterCallStatsEntry 34 }

--   
-- Summary Statistics   
--   

ipuSIPSummaryStatsTable OBJECT-TYPE   
    SYNTAX     SEQUENCE OF IpuSIPSummaryStatsEntry   
    MAX-ACCESS not-accessible   
    STATUS     current   
    DESCRIPTION   
         "This table contains the summary statistics objects   
          applicable to all SIP entities.  Each row represents   
          those objects for a particular SIP entity present in   
          this system."  
    ::= { ipuSIP 1 }   
   
ipuSIPSummaryStatsEntry OBJECT-TYPE   
    SYNTAX     IpuSIPSummaryStatsEntry   
    MAX-ACCESS not-accessible   
    STATUS     current   
    DESCRIPTION   
         "A row of summary statistics. 

          Each row represents those objects for a particular SIP  
          entity present in this system.  applIndex is used to  
          uniquely identify these instances of SIP entities and  
          correlate them through the common framework of the  
          NETWORK-SERVICES-MIB (RFC 2788)." 
    INDEX { applIndex }   
    ::= { ipuSIPSummaryStatsTable 1 }   
      
IpuSIPSummaryStatsEntry ::=   
    SEQUENCE {   
          ipuSIPSummaryInRequests         Counter32,   
          ipuSIPSummaryOutRequests        Counter32,   
          ipuSIPSummaryInResponses        Counter32,   
          ipuSIPSummaryOutResponses       Counter32,   
          ipuSIPSummaryTotalTransactions  Counter32   
    }   
   
ipuSIPSummaryInRequests OBJECT-TYPE   
    SYNTAX     Counter32   
    MAX-ACCESS read-only   
    STATUS     current   
    DESCRIPTION   
         "This object indicates the total number of SIP request   
          messages received by the SIP entity including   
          retransmissions."   
    ::= { ipuSIPSummaryStatsEntry 1 }   
      
ipuSIPSummaryOutRequests OBJECT-TYPE   
    SYNTAX     Counter32   
    MAX-ACCESS read-only   
    STATUS     current   
    DESCRIPTION   
         "This object contains the total number of SIP request   
          messages sent out (originated and relayed) by the SIP   
          entity.  Where a particular message is sent more than   
          once, for example as a retransmission, or as a result of   
          forking, each transmission is counted separately."   
    ::= { ipuSIPSummaryStatsEntry 2 }   
   
ipuSIPSummaryInResponses OBJECT-TYPE   
    SYNTAX     Counter32   
    MAX-ACCESS read-only   
    STATUS     current   
    DESCRIPTION   
         "This object contains the total number of SIP response   
          messages received by the SIP entity including   
          retransmissions."   
    ::= { ipuSIPSummaryStatsEntry 3 }   
   
ipuSIPSummaryOutResponses OBJECT-TYPE   
    SYNTAX     Counter32   
    MAX-ACCESS read-only   
    STATUS     current   
    DESCRIPTION   
         "This object contains the total number of SIP response   
          messages sent (originated and relayed) by the SIP entity   
          including retransmissions."   
    ::= { ipuSIPSummaryStatsEntry 4 }   
    
ipuSIPSummaryTotalTransactions OBJECT-TYPE   
    SYNTAX Counter32   
    MAX-ACCESS read-only   
    STATUS current   
    DESCRIPTION   
         "This object contains a count of the number of transactions   
          completed or in progress.   
      
          A SIP transaction occurs between a client and a server and   
          comprises all messages from the first request sent from   
          the client to the server up to a final (non-1xx) response   
          sent from the server to the client.   
   
          A transaction is identified by the CSeq sequence number   
          within a single call leg.  The ACK request has the same   
          CSeq number as the corresponding INVITE request, but   
          comprises a transaction of its own.   
   
          In the case of a forked request, all branches count as a   
          single transaction."   
    ::= { ipuSIPSummaryStatsEntry 5 }   

--  
-- SIP Method Statistics   
-- Total counts for each SIP method.   
--   

ipuSIPMethodStatsTable OBJECT-TYPE   
    SYNTAX     SEQUENCE OF IpuSIPMethodStatsEntry   
    MAX-ACCESS not-accessible   
    STATUS     current   
    DESCRIPTION   
         "This table contains the per method statistics objects   
          applicable to all SIP entities.  Each row represents   
          those objects for a particular SIP entity present in   
          this system."   
    ::= { ipuSIP 2 }   
      
ipuSIPMethodStatsEntry OBJECT-TYPE   
    SYNTAX     IpuSIPMethodStatsEntry   
    MAX-ACCESS not-accessible   
    STATUS     current   
    DESCRIPTION   
         "A row of per method statistics. 

          Each row represents those objects for a particular SIP  
          entity present in this system.  applIndex is used to  
          uniquely identify these instances of SIP entities and  
          correlate them through the common framework of the  
          NETWORK-SERVICES-MIB (RFC 2788)." 
    INDEX { applIndex }   
    ::= { ipuSIPMethodStatsTable 1 }   
   
IpuSIPMethodStatsEntry ::=   
    SEQUENCE {   
          ipuSIPStatsInviteIns          Counter32,   
          ipuSIPStatsInviteOuts         Counter32,   
          ipuSIPStatsAckIns             Counter32,   
          ipuSIPStatsAckOuts            Counter32,   
          ipuSIPStatsByeIns             Counter32,   
          ipuSIPStatsByeOuts            Counter32,   
          ipuSIPStatsCancelIns          Counter32,   
          ipuSIPStatsCancelOuts         Counter32,   
          ipuSIPStatsOptionsIns         Counter32,   
          ipuSIPStatsOptionsOuts        Counter32,   
          ipuSIPStatsRegisterIns        Counter32,   
          ipuSIPStatsRegisterOuts       Counter32,   
          ipuSIPStatsInfoIns            Counter32,   
          ipuSIPStatsInfoOuts           Counter32   
    }   
   
ipuSIPStatsInviteIns OBJECT-TYPE   
    SYNTAX      Counter32   
    MAX-ACCESS  read-only   
    STATUS      current   
    DESCRIPTION   
         "This object reflects the total number of INVITE requests   
          received by the SIP entity including retransmissions."   
    ::= { ipuSIPMethodStatsEntry 1 }   
   
ipuSIPStatsInviteOuts OBJECT-TYPE   
    SYNTAX      Counter32   
    MAX-ACCESS  read-only   
    STATUS      current   
   
    DESCRIPTION   
         "This object reflects the total number of INVITE requests   
          sent by the SIP entity including retransmissions."   
    ::= { ipuSIPMethodStatsEntry 2 }   
      
ipuSIPStatsAckIns OBJECT-TYPE   
    SYNTAX      Counter32   
    MAX-ACCESS  read-only   
    STATUS      current   
    DESCRIPTION   
         "This object reflects the total number of ACK requests   
          received by the SIP entity." 
    ::= { ipuSIPMethodStatsEntry 3 }   
   
ipuSIPStatsAckOuts OBJECT-TYPE   
    SYNTAX      Counter32   
    MAX-ACCESS  read-only   
    STATUS      current   
    DESCRIPTION   
         "This object reflects the total number of ACK requests sent   
          by the SIP entity."   
    ::= { ipuSIPMethodStatsEntry 4 }   
      
ipuSIPStatsByeIns OBJECT-TYPE   
    SYNTAX      Counter32   
    MAX-ACCESS  read-only   
    STATUS      current   
    DESCRIPTION   
         "This object reflects the total number of BYE requests   
          received by the SIP entity including retransmissions."   
    ::= { ipuSIPMethodStatsEntry 5 }   
      
ipuSIPStatsByeOuts OBJECT-TYPE   
    SYNTAX      Counter32   
    MAX-ACCESS  read-only   
    STATUS      current   
    DESCRIPTION   
         "This object reflects the total number of BYE requests sent   
          by the SIP entity including retransmissions."   
    ::= { ipuSIPMethodStatsEntry 6 }   
      
ipuSIPStatsCancelIns OBJECT-TYPE   
    SYNTAX      Counter32   
    MAX-ACCESS  read-only   
    STATUS      current   
    DESCRIPTION   
         "This object reflects the total number of CANCEL requests   
          received by the SIP entity including retransmissions."   
    ::= { ipuSIPMethodStatsEntry 7 }   
      
ipuSIPStatsCancelOuts OBJECT-TYPE   
    SYNTAX      Counter32   
    MAX-ACCESS  read-only   
    STATUS      current   
    DESCRIPTION   
         "This object reflects the total number of CANCEL requests   
          sent by the SIP entity including retransmissions."   
    ::= { ipuSIPMethodStatsEntry 8 }   
      
ipuSIPStatsOptionsIns OBJECT-TYPE   
    SYNTAX      Counter32   
    MAX-ACCESS  read-only   
    STATUS      current   
    DESCRIPTION   
         "This object reflects the total number of OPTIONS requests   
          received by the SIP entity including retransmissions."   
    ::= { ipuSIPMethodStatsEntry 9 }   
      
ipuSIPStatsOptionsOuts OBJECT-TYPE   
    SYNTAX      Counter32   
    MAX-ACCESS  read-only   
    STATUS      current   
    DESCRIPTION   
         "This object reflects the total number of OPTIONS requests   
          sent by the SIP entity including retransmissions."   
    ::= { ipuSIPMethodStatsEntry 10 }   
   
ipuSIPStatsRegisterIns OBJECT-TYPE   
    SYNTAX      Counter32   
    MAX-ACCESS  read-only   
    STATUS      current   
    DESCRIPTION   
         "This object reflects the total number of REGISTER requests   
          received by the SIP entity including retransmissions."   
    ::= { ipuSIPMethodStatsEntry 11 }   
   
ipuSIPStatsRegisterOuts OBJECT-TYPE   
    SYNTAX      Counter32   
    MAX-ACCESS  read-only   
    STATUS      current   
    DESCRIPTION   
         "This object reflects the total number of REGISTER requests   
          sent by the SIP entity including retransmissions."   
    ::= { ipuSIPMethodStatsEntry 12 }   
  
ipuSIPStatsInfoIns OBJECT-TYPE   
    SYNTAX      Counter32   
    MAX-ACCESS  read-only   
    STATUS      current   
    DESCRIPTION   
         "This object reflects the total number of INFO requests   
          received by the SIP entity including retransmissions."   
    ::= { ipuSIPMethodStatsEntry 13 }   
      
ipuSIPStatsInfoOuts OBJECT-TYPE   
    SYNTAX      Counter32   
    MAX-ACCESS  read-only   
    STATUS      current   
    DESCRIPTION   
         "This object reflects the total number of INFO requests   
          sent by the SIP entity including retransmissions."   
    ::= { ipuSIPMethodStatsEntry 14 }   
      
--   
-- SIP Response Status Codes   
--   

ipuSIPStatusCodesTable OBJECT-TYPE   
    SYNTAX      SEQUENCE OF IpuSIPStatusCodesEntry   
    MAX-ACCESS  not-accessible   
    STATUS      current   
    DESCRIPTION    
         "This table contains statistics on response status code    
          classes for each SIP entity in this system." 
    ::= { ipuSIP 3 }   
   
ipuSIPStatusCodesEntry OBJECT-TYPE   
    SYNTAX      IpuSIPStatusCodesEntry   
    MAX-ACCESS  not-accessible   
    STATUS      current   
    DESCRIPTION   
         "This row contains statistics on response status codes. 
          Each row represents those objects for a particular SIP  
          entity present in this system.  applIndex is used to  
          uniquely identify these instances of SIP entities and  
          correlate them through the common framework of the  
          NETWORK-SERVICES-MIB (RFC 2788)." 
    INDEX { applIndex }   
    ::= { ipuSIPStatusCodesTable 1 }   
   
IpuSIPStatusCodesEntry ::=   
    SEQUENCE {   
          ipuSIPStatsInfoClassIns          Counter32,   
          ipuSIPStatsInfoClassOuts         Counter32,   
          ipuSIPStatsSuccessClassIns       Counter32,   
          ipuSIPStatsSuccessClassOuts      Counter32,   
          ipuSIPStatsRedirClassIns         Counter32,   
          ipuSIPStatsRedirClassOuts        Counter32,   
          ipuSIPStatsReqFailClassIns       Counter32,   
          ipuSIPStatsReqFailClassOuts      Counter32,   
          ipuSIPStatsServerFailClassIns    Counter32,   
          ipuSIPStatsServerFailClassOuts   Counter32,   
          ipuSIPStatsGlobalFailClassIns    Counter32,   
          ipuSIPStatsGlobalFailClassOuts   Counter32   
    }   
   
ipuSIPStatsInfoClassIns OBJECT-TYPE   
    SYNTAX      Counter32   
    MAX-ACCESS  read-only   
    STATUS      current   
    DESCRIPTION   
         "This object reflects the number of 1xx class    
          SIP responses received by the SIP entity.   
          This class of responses relates to providing some   
          information concerning the progress of processing   
          a SIP request."   
    ::= { ipuSIPStatusCodesEntry 1 }   
   
ipuSIPStatsInfoClassOuts OBJECT-TYPE   
    SYNTAX      Counter32   
    MAX-ACCESS  read-only   
    STATUS      current   
    DESCRIPTION   
         "This object reflects the number of 1xx class    
          SIP responses sent by the SIP entity.   
   
          This class of responses relates to providing some   
          information concerning the progress of processing   
          a SIP request."   
    ::= { ipuSIPStatusCodesEntry 2 }   
   
ipuSIPStatsSuccessClassIns OBJECT-TYPE   
    SYNTAX      Counter32   
    MAX-ACCESS  read-only   
    STATUS      current   
    DESCRIPTION   
         "This object reflects the number of 2xx class SIP    
          responses received by the SIP entity. This class of    
          responses relate to successful completion of a SIP    
          request."   
    ::= { ipuSIPStatusCodesEntry 3 }   
      
ipuSIPStatsSuccessClassOuts OBJECT-TYPE   
    SYNTAX      Counter32   
    MAX-ACCESS  read-only   
    STATUS      current   
    DESCRIPTION   
         "This object reflects the number of 2xx class SIP    
          responses sent by the SIP entity. This class of    
          responses relate to successful completion of a SIP    
          request."   
    ::= { ipuSIPStatusCodesEntry 4 }   
      
ipuSIPStatsRedirClassIns OBJECT-TYPE   
    SYNTAX      Counter32   
    MAX-ACCESS  read-only   
    STATUS      current   
    DESCRIPTION   
         "This object reflects the number of 3xx class SIP    
          responses received by the SIP entity. This class of    
          responses relate to call redirection actions taken   
          by a Redirect Server."   
    ::= { ipuSIPStatusCodesEntry 5 }   
      
ipuSIPStatsRedirClassOuts OBJECT-TYPE   
    SYNTAX      Counter32   
    MAX-ACCESS  read-only   
    STATUS      current   
    DESCRIPTION   
         "This object reflects the number of 3xx class SIP    
          responses sent by the SIP entity. This class of    
          responses relate to call redirection actions taken   
          by a Redirect Server."   
    ::= { ipuSIPStatusCodesEntry 6 }   
   
ipuSIPStatsReqFailClassIns OBJECT-TYPE   
    SYNTAX      Counter32   
    MAX-ACCESS  read-only   
    STATUS      current   
    DESCRIPTION   
         "This object reflects the number of 4xx class SIP    
          responses received by the SIP entity. This class of    
          responses reflect request failure by a SIP entity   
          providing a client function."   
    ::= { ipuSIPStatusCodesEntry 7 }   
   
ipuSIPStatsReqFailClassOuts OBJECT-TYPE   
    SYNTAX      Counter32   
    MAX-ACCESS  read-only   
    STATUS      current   
    DESCRIPTION   
         "This object reflects the number of 4xx class SIP    
          responses sent by the SIP entity. This class of    
          responses reflect request failure by a SIP entity   
          providing a server function."   
    ::= { ipuSIPStatusCodesEntry 8 }   
      
ipuSIPStatsServerFailClassIns OBJECT-TYPE   
    SYNTAX      Counter32   
    MAX-ACCESS  read-only   
    STATUS      current   
    DESCRIPTION   
         "This object reflects the number of 5xx class SIP    
          responses received by the SIP entity. This class of    
          responses reflect failure responses received by a    
          SIP entity providing a client function.  These    
          responses are not definite failures and must not    
          terminate a search if other possible locations remain   
          untried."   
    ::= { ipuSIPStatusCodesEntry 9 }   
      
ipuSIPStatsServerFailClassOuts OBJECT-TYPE   
    SYNTAX      Counter32   
    MAX-ACCESS  read-only   
    STATUS      current   
    DESCRIPTION   
         "This object reflects the number of 5xx class SIP    
          responses sent by the SIP entity. This class of    
          responses reflect failure responses sent by a SIP   
          entity providing a server function.  These    
          responses are not definite failures and must not    
          terminate a search if other possible locations remain   
          untried."   
    ::= { ipuSIPStatusCodesEntry 10 }   
      
ipuSIPStatsGlobalFailClassIns OBJECT-TYPE   
    SYNTAX      Counter32   
    MAX-ACCESS  read-only   
    STATUS      current   
    DESCRIPTION   
         "This object reflects the number of 6xx class SIP    
          responses received by the SIP entity. This class of    
          responses reflect failure responses received by a    
          SIP entity providing a client function.   
             
          The responses generally indicate that a server has    
          definitive information about a particular called party,   
          not just the particular instance indicated in the    
          Request-URI.  All further searches for this user are    
          doomed to failure and pending searches should be    
          terminated."   
    ::= { ipuSIPStatusCodesEntry 11 }   
   
ipuSIPStatsGlobalFailClassOuts OBJECT-TYPE   
    SYNTAX      Counter32   
    MAX-ACCESS  read-only   
    STATUS      current   
    DESCRIPTION   
         "This object reflects the number of 6xx class SIP    
          responses sent by the SIP entity. This class of    
          responses reflect failure responses sent by a SIP   
          entity providing a server function.   
                
          The responses generally indicate that a server has    
          definitive information about a particular called party,   
          not just the particular instance indicated in the    
          Request-URI.  All further searches for this user are    
          doomed to failure and pending searches should be    
          terminated."   
    ::= { ipuSIPStatusCodesEntry 12 }   

--  
-- SIP Method Duplicate Statistics   
-- Total counts of retrnsmitted messages for each SIP method.   
--   

ipuSIPMethodDupStatsTable OBJECT-TYPE   
    SYNTAX     SEQUENCE OF IpuSIPMethodDupStatsEntry   
    MAX-ACCESS not-accessible   
    STATUS     current   
    DESCRIPTION   
         "This table contains the per method retrnsmitted message statistics 
          objects applicable to all SIP entities.  Each row represents 
          those objects for a particular SIP entity present in   
          this system."   
    ::= { ipuSIP 4 }   
      
ipuSIPMethodDupStatsEntry OBJECT-TYPE   
    SYNTAX     IpuSIPMethodDupStatsEntry   
    MAX-ACCESS not-accessible   
    STATUS     current   
    DESCRIPTION   
         "A row of per method retransmitted message statistics. 

          Each row represents those objects for a particular SIP  
          entity present in this system.  applIndex is used to  
          uniquely identify these instances of SIP entities and  
          correlate them through the common framework of the  
          NETWORK-SERVICES-MIB (RFC 2788)." 
    INDEX { applIndex }   
    ::= { ipuSIPMethodDupStatsTable 1 }   
   
IpuSIPMethodDupStatsEntry ::=   
    SEQUENCE {   
          ipuSIPStatsDupInviteIns          Counter32,   
          ipuSIPStatsDupInviteOuts         Counter32,   
          ipuSIPStatsDupAckIns             Counter32,   
          ipuSIPStatsDupAckOuts            Counter32,   
          ipuSIPStatsDupByeIns             Counter32,   
          ipuSIPStatsDupByeOuts            Counter32,   
          ipuSIPStatsDupCancelIns          Counter32,   
          ipuSIPStatsDupCancelOuts         Counter32,   
          ipuSIPStatsDupOptionsIns         Counter32,   
          ipuSIPStatsDupOptionsOuts        Counter32,   
          ipuSIPStatsDupRegisterIns        Counter32,   
          ipuSIPStatsDupRegisterOuts       Counter32,   
          ipuSIPStatsDupInfoIns            Counter32,   
          ipuSIPStatsDupInfoOuts           Counter32   
    }   
   
ipuSIPStatsDupInviteIns OBJECT-TYPE   
    SYNTAX      Counter32   
    MAX-ACCESS  read-only   
    STATUS      current   
    DESCRIPTION   
         "This object reflects the total number of duplicate INVITE requests   
          received by the SIP entity including retransmissions."   
    ::= { ipuSIPMethodDupStatsEntry 1 }   
   
ipuSIPStatsDupInviteOuts OBJECT-TYPE   
    SYNTAX      Counter32   
    MAX-ACCESS  read-only   
    STATUS      current   
    DESCRIPTION   
         "This object reflects the total number of duplicate INVITE requests   
          sent by the SIP entity including retransmissions."   
    ::= { ipuSIPMethodDupStatsEntry 2 }   
      
ipuSIPStatsDupAckIns OBJECT-TYPE   
    SYNTAX      Counter32   
    MAX-ACCESS  read-only   
    STATUS      current   
    DESCRIPTION   
         "This object reflects the total number of duplicate ACK requests   
          received by the SIP entity." 
    ::= { ipuSIPMethodDupStatsEntry 3 }   
   
ipuSIPStatsDupAckOuts OBJECT-TYPE   
    SYNTAX      Counter32   
    MAX-ACCESS  read-only   
    STATUS      current   
    DESCRIPTION   
         "This object reflects the total number of duplicate ACK requests 
          sent by the SIP entity."   
    ::= { ipuSIPMethodDupStatsEntry 4 }   
      
ipuSIPStatsDupByeIns OBJECT-TYPE   
    SYNTAX      Counter32   
    MAX-ACCESS  read-only   
    STATUS      current   
    DESCRIPTION   
         "This object reflects the total number of duplicate BYE requests   
          received by the SIP entity including retransmissions."   
    ::= { ipuSIPMethodDupStatsEntry 5 }   
      
ipuSIPStatsDupByeOuts OBJECT-TYPE   
    SYNTAX      Counter32   
    MAX-ACCESS  read-only   
    STATUS      current   
    DESCRIPTION   
         "This object reflects the total number of duplicate BYE requests 
          sent by the SIP entity including retransmissions."   
    ::= { ipuSIPMethodDupStatsEntry 6 }   
      
ipuSIPStatsDupCancelIns OBJECT-TYPE   
    SYNTAX      Counter32   
    MAX-ACCESS  read-only   
    STATUS      current   
    DESCRIPTION   
         "This object reflects the total number of duplicate CANCEL requests   
          received by the SIP entity including retransmissions."   
    ::= { ipuSIPMethodDupStatsEntry 7 }   
      
ipuSIPStatsDupCancelOuts OBJECT-TYPE   
    SYNTAX      Counter32   
    MAX-ACCESS  read-only   
    STATUS      current   
    DESCRIPTION   
         "This object reflects the total number of duplicate CANCEL requests   
          sent by the SIP entity including retransmissions."   
    ::= { ipuSIPMethodDupStatsEntry 8 }   
      
ipuSIPStatsDupOptionsIns OBJECT-TYPE   
    SYNTAX      Counter32   
    MAX-ACCESS  read-only   
    STATUS      current   
    DESCRIPTION   
         "This object reflects the total number of duplicate OPTIONS requests   
          received by the SIP entity including retransmissions."   
    ::= { ipuSIPMethodDupStatsEntry 9 }   
      
ipuSIPStatsDupOptionsOuts OBJECT-TYPE   
    SYNTAX      Counter32   
    MAX-ACCESS  read-only   
    STATUS      current   
    DESCRIPTION   
         "This object reflects the total number of duplicate OPTIONS requests   
          sent by the SIP entity including retransmissions."   
    ::= { ipuSIPMethodDupStatsEntry 10 }   
   
ipuSIPStatsDupRegisterIns OBJECT-TYPE   
    SYNTAX      Counter32   
    MAX-ACCESS  read-only   
    STATUS      current   
    DESCRIPTION   
         "This object reflects the total number of duplicate REGISTER requests 
          received by the SIP entity including retransmissions."   
    ::= { ipuSIPMethodDupStatsEntry 11 }   
   
ipuSIPStatsDupRegisterOuts OBJECT-TYPE   
    SYNTAX      Counter32   
    MAX-ACCESS  read-only   
    STATUS      current   
    DESCRIPTION   
         "This object reflects the total number of duplicate REGISTER requests 
          sent by the SIP entity including retransmissions."   
    ::= { ipuSIPMethodDupStatsEntry 12 }   
  
ipuSIPStatsDupInfoIns OBJECT-TYPE   
    SYNTAX      Counter32   
    MAX-ACCESS  read-only   
    STATUS      current   
    DESCRIPTION   
         "This object reflects the total number of duplicate INFO requests   
          received by the SIP entity including retransmissions."   
    ::= { ipuSIPMethodDupStatsEntry 13 }   
      
ipuSIPStatsDupInfoOuts OBJECT-TYPE   
    SYNTAX      Counter32   
    MAX-ACCESS  read-only   
    STATUS      current   
    DESCRIPTION   
         "This object reflects the total number of duplicate INFO requests   
          sent by the SIP entity including retransmissions."   
    ::= { ipuSIPMethodDupStatsEntry 14 }   
      
--   
-- SIP Response Status Codes, Table for number of retransmitted messages 
--   

ipuSIPStatusCodesDupTable OBJECT-TYPE   
    SYNTAX      SEQUENCE OF IpuSIPStatusCodesDupEntry   
    MAX-ACCESS  not-accessible   
    STATUS      current   
    DESCRIPTION    
         "This table contains statistics on retransmitted 
          response status code classes for each SIP entity in 
          this system." 
    ::= { ipuSIP 5 }   
   
ipuSIPStatusCodesDupEntry OBJECT-TYPE   
    SYNTAX      IpuSIPStatusCodesDupEntry   
    MAX-ACCESS  not-accessible   
    STATUS      current   
    DESCRIPTION   
         "This row contains statistics on duplicate response status codes. 
          Each row represents those objects for a particular SIP  
          entity present in this system.  applIndex is used to  
          uniquely identify these instances of SIP entities and  
          correlate them through the common framework of the  
          NETWORK-SERVICES-MIB (RFC 2788)." 
    INDEX { applIndex }   
    ::= { ipuSIPStatusCodesDupTable 1 }   
   
IpuSIPStatusCodesDupEntry ::=   
    SEQUENCE {   
          ipuSIPStatsDupInfoClassIns          Counter32,   
          ipuSIPStatsDupInfoClassOuts         Counter32,   
          ipuSIPStatsDupSuccessClassIns       Counter32,   
          ipuSIPStatsDupSuccessClassOuts      Counter32,   
          ipuSIPStatsDupRedirClassIns         Counter32,   
          ipuSIPStatsDupRedirClassOuts        Counter32,   
          ipuSIPStatsDupReqFailClassIns       Counter32,   
          ipuSIPStatsDupReqFailClassOuts      Counter32,   
          ipuSIPStatsDupServerFailClassIns    Counter32,   
          ipuSIPStatsDupServerFailClassOuts   Counter32,   
          ipuSIPStatsDupGlobalFailClassIns    Counter32,   
          ipuSIPStatsDupGlobalFailClassOuts   Counter32   
    }   
   
ipuSIPStatsDupInfoClassIns OBJECT-TYPE   
    SYNTAX      Counter32   
    MAX-ACCESS  read-only   
    STATUS      current   
    DESCRIPTION   
         "This object reflects the number of duplicate 1xx class    
          SIP responses received by the SIP entity."
    ::= { ipuSIPStatusCodesDupEntry 1 }   
   
ipuSIPStatsDupInfoClassOuts OBJECT-TYPE   
    SYNTAX      Counter32   
    MAX-ACCESS  read-only   
    STATUS      current   
    DESCRIPTION   
         "This object reflects the number of duplicate 1xx class    
          SIP responses sent by the SIP entity."
    ::= { ipuSIPStatusCodesDupEntry 2 }   
   
ipuSIPStatsDupSuccessClassIns OBJECT-TYPE   
    SYNTAX      Counter32   
    MAX-ACCESS  read-only   
    STATUS      current   
    DESCRIPTION   
         "This object reflects the number of duplicate 2xx class SIP    
          responses received by the SIP entity. "
    ::= { ipuSIPStatusCodesDupEntry 3 }   
      
ipuSIPStatsDupSuccessClassOuts OBJECT-TYPE   
    SYNTAX      Counter32   
    MAX-ACCESS  read-only   
    STATUS      current   
    DESCRIPTION   
         "This object reflects the number of duplicate 2xx class SIP    
          responses sent by the SIP entity."
    ::= { ipuSIPStatusCodesDupEntry 4 }   
      
ipuSIPStatsDupRedirClassIns OBJECT-TYPE   
    SYNTAX      Counter32   
    MAX-ACCESS  read-only   
    STATUS      current   
    DESCRIPTION   
         "This object reflects the number of duplicate 3xx class SIP    
          responses received by the SIP entity."
    ::= { ipuSIPStatusCodesDupEntry 5 }   
      
ipuSIPStatsDupRedirClassOuts OBJECT-TYPE   
    SYNTAX      Counter32   
    MAX-ACCESS  read-only   
    STATUS      current   
    DESCRIPTION   
         "This object reflects the number of duplicate 3xx class SIP    
          responses sent by the SIP entity."
    ::= { ipuSIPStatusCodesDupEntry 6 }   
   
ipuSIPStatsDupReqFailClassIns OBJECT-TYPE   
    SYNTAX      Counter32   
    MAX-ACCESS  read-only   
    STATUS      current   
    DESCRIPTION   
         "This object reflects the number of duplicate 4xx class SIP    
          responses received by the SIP entity."
    ::= { ipuSIPStatusCodesDupEntry 7 }   
   
ipuSIPStatsDupReqFailClassOuts OBJECT-TYPE   
    SYNTAX      Counter32   
    MAX-ACCESS  read-only   
    STATUS      current   
    DESCRIPTION   
         "This object reflects the number of duplicate 4xx class SIP    
          responses sent by the SIP entity."
    ::= { ipuSIPStatusCodesDupEntry 8 }   
      
ipuSIPStatsDupServerFailClassIns OBJECT-TYPE   
    SYNTAX      Counter32   
    MAX-ACCESS  read-only   
    STATUS      current   
    DESCRIPTION   
         "This object reflects the number of duplicate 5xx class SIP    
          responses received by the SIP entity."
    ::= { ipuSIPStatusCodesDupEntry 9 }   
      
ipuSIPStatsDupServerFailClassOuts OBJECT-TYPE   
    SYNTAX      Counter32   
    MAX-ACCESS  read-only   
    STATUS      current   
    DESCRIPTION   
         "This object reflects the number of duplicate 5xx class SIP    
          responses sent by the SIP entity."
    ::= { ipuSIPStatusCodesDupEntry 10 }   
      
ipuSIPStatsDupGlobalFailClassIns OBJECT-TYPE   
    SYNTAX      Counter32   
    MAX-ACCESS  read-only   
    STATUS      current   
    DESCRIPTION   
         "This object reflects the number of duplicate 6xx class SIP    
          responses received by the SIP entity."
    ::= { ipuSIPStatusCodesDupEntry 11 }   
   
ipuSIPStatsDupGlobalFailClassOuts OBJECT-TYPE   
    SYNTAX      Counter32   
    MAX-ACCESS  read-only   
    STATUS      current   
    DESCRIPTION   
         "This object reflects the number of duplicate 6xx class SIP    
          responses sent by the SIP entity."
    ::= { ipuSIPStatusCodesDupEntry 12 }   

ipuMGCPInBadVersions OBJECT-TYPE
    SYNTAX      Counter32
    MAX-ACCESS  read-only
    STATUS      current
    DESCRIPTION
        "The total number of incoming messages which were delivered to the App
         Server and were for an unsupported protocol version."
    ::= { ipuMGCPScalars 1 }

ipuMGCPUnRecognizedPackets OBJECT-TYPE
    SYNTAX      Counter32
    MAX-ACCESS  read-only
    STATUS      current
    DESCRIPTION
        "This refers to the count of unrecognized packets since reset."
    ::= { ipuMGCPScalars 2 }

ipuMGCPOperStatus OBJECT-TYPE
    SYNTAX      INTEGER {
                up (1),
                down (2)
                }
    MAX-ACCESS  read-only
    STATUS      current
    DESCRIPTION
        "This object indicates the current operational status of the protocol
         entity.
         The possible operating status are :
              up - protocol up
              down - protocol down
        "
    ::= { ipuMGCPScalars 3 }

ipuMGCPRequestTimeOut OBJECT-TYPE
    SYNTAX      Integer32 (1..10000)
    UNITS       "milliseconds"
    MAX-ACCESS  read-write
    STATUS      current
    DESCRIPTION
        "This request timeout is used to determine the timeout value used for
         retransmitting unacknowledged message.
         It is the responsibility of the requesting entity to provide 
         suitable timeouts for all outstanding commands, and to retry 
         commands when timeouts exceeded.

         The default value of this object is 500 milliseconds."
    ::= { ipuMGCPScalars 4 }

ipuMGCPRequestRetries OBJECT-TYPE
    SYNTAX      Integer32 (0..10)
    MAX-ACCESS  read-write
    STATUS      current
    DESCRIPTION
        "This object specifies the number of retries for a request that 
         exceeds timeout. The default value of this object is 3."
    ::= { ipuMGCPScalars 5 }

ipuMGCPLowerBoundForPacketLoss OBJECT-TYPE
    SYNTAX      Integer32 (1..3000)
    MAX-ACCESS  read-write
    STATUS      current
    DESCRIPTION
        "This object specifies the lower bound for voice quality packet
         loss per 100,000 packets. Voice quality packet loss may happen
         due to network congestion or due to network overload."
    ::= { ipuMGCPScalars 6 }

ipuMGCPHigherBoundForPacketLoss OBJECT-TYPE
    SYNTAX      Integer32 (5000..25000)
    MAX-ACCESS  read-write
    STATUS      current
    DESCRIPTION
        "This object specifies the higher bound for voice quality packet
         loss per 100,000 packets. Voice quality packet loss may happen
         due to network congestion or due to network overload."
    ::= { ipuMGCPScalars 7 }

ipuMGCPLowerBoundForJitter OBJECT-TYPE
    SYNTAX      Integer32 (4..60)
    UNITS       "milliseconds"
    MAX-ACCESS  read-write
    STATUS      current
    DESCRIPTION
        "This object is the lower bound for Quality Alert for jitter.

         Jitter is an estimate of the statistical variance of the RTP
         data packet interval-rival time measured in milliseconds and
         expressed as an unsigned integer.

         The default value of this object is 30."
    ::= { ipuMGCPScalars 8 }

ipuMGCPHigherBoundForJitter OBJECT-TYPE
    SYNTAX      Integer32 (100..200)
    UNITS       "milliseconds"
    MAX-ACCESS  read-write
    STATUS      current
    DESCRIPTION
        "This object is the higher bound for Quality Alert for jitter.
         The default value of this object is 150."
    ::= { ipuMGCPScalars 9 }

ipuMGCPLowerBoundForLatency OBJECT-TYPE
    SYNTAX      Integer32 (125..200)
    UNITS       "milliseconds"
    MAX-ACCESS  read-write
    STATUS      current
    DESCRIPTION
        "This object is the lower bound for Quality Alert for latency.

         QA latency is an estimate of the network delay, expressed in
         milliseconds. This is the average value of the difference
         between the Network Time Protocol (NTP) timestamp indicated
         by the senders of the RTCP messages and the NTP timestamp
         of the receivers, measured when these messages are received.

         The default value of this object is 150."
    ::= { ipuMGCPScalars 10 }

ipuMGCPHigherBoundForLatency OBJECT-TYPE
    SYNTAX      Integer32 (250..400)
    UNITS       "milliseconds"
    MAX-ACCESS  read-write
    STATUS      current
    DESCRIPTION
        "This object is the higher bound for Quality Alert for latency.
         The default value of this object is 300."
    ::= { ipuMGCPScalars 11 }

ipuMGCPMsgStatsTable OBJECT-TYPE
    SYNTAX      SEQUENCE OF IpuMGCPMsgStatsEntry
    MAX-ACCESS  not-accessible
    STATUS      current
    DESCRIPTION
        "This table contains MGCP statistics information. MGCP statistics are
         kept in this table, with each table entry containing the statistics
         of MGCP that communicates with a Media Gateway Controller (MGC) at a
         specific IP address of the MGC."
    ::= { ipuMGCPTables 1 }

ipuMGCPMsgStatsEntry OBJECT-TYPE
    SYNTAX      IpuMGCPMsgStatsEntry
    MAX-ACCESS  not-accessible
    STATUS      current
    DESCRIPTION
        "The row of the ipuMGCPMsgStatsTable contains information about MGCP
         statstics per IP address of the Media Gateway Controller."
    INDEX { ipuMGCPMGCAddr , ipuMGCPMsgType }
    ::= { ipuMGCPMsgStatsTable 1 }

IpuMGCPMsgStatsEntry ::= SEQUENCE {
         ipuMGCPMGCAddr                         IpAddress,
         ipuMGCPMsgType				INTEGER,
         ipuMGCPSuccessCmdsSent                 Counter32,
         ipuMGCPSuccessCmdsReceived             Counter32,
         ipuMGCPRetranCmdsSent                  Counter32,
         ipuMGCPRetranCmdsReceived              Counter32,
         ipuMGCPBadformatCmdsReceived           Counter32,
         ipuMGCPFailedCmdsSent                  Counter32,
         ipuMGCPSuccessResponsesSent            Counter32,
         ipuMGCPSuccessResponsesReceived        Counter32,
         ipuMGCPRetranResponsesSent             Counter32,
         ipuMGCPRetranResponsesReceived         Counter32,
         ipuMGCPBadformatResponsesReceived      Counter32
     }

ipuMGCPMGCAddr OBJECT-TYPE
    SYNTAX      IpAddress
    MAX-ACCESS  not-accessible
    STATUS      current
    DESCRIPTION
        "This object specifies the IP address of the Media Gateway
         Controller."
    ::= { ipuMGCPMsgStatsEntry 1 }

ipuMGCPMsgType OBJECT-TYPE
    SYNTAX      INTEGER {
                    crcx (1),
                    mdcx (2),
                    dlcx (3),
                    rqnt (4),
                    ntfy (5),
                    auep (6),
                    aucx (7),
                    rsip (8),
                    epcf (9),
                    other (10)
                }
    MAX-ACCESS  not-accessible
    STATUS      current
    DESCRIPTION
        "Type of the MGCP message."
    ::= { ipuMGCPMsgStatsEntry 2 }

ipuMGCPSuccessCmdsSent OBJECT-TYPE
    SYNTAX      Counter32
    MAX-ACCESS  read-only
    STATUS      current
    DESCRIPTION
         ""
    ::= { ipuMGCPMsgStatsEntry 3 }

ipuMGCPSuccessCmdsReceived OBJECT-TYPE
    SYNTAX      Counter32
    MAX-ACCESS  read-only
    STATUS      current
    DESCRIPTION
         ""
    ::= { ipuMGCPMsgStatsEntry 4 }

ipuMGCPRetranCmdsSent OBJECT-TYPE
    SYNTAX      Counter32
    MAX-ACCESS  read-only
    STATUS      current
    DESCRIPTION
         ""
    ::= { ipuMGCPMsgStatsEntry 5 }

ipuMGCPRetranCmdsReceived OBJECT-TYPE
    SYNTAX      Counter32
    MAX-ACCESS  read-only
    STATUS      current
    DESCRIPTION
         ""
    ::= { ipuMGCPMsgStatsEntry 6 }

ipuMGCPBadformatCmdsReceived OBJECT-TYPE
    SYNTAX      Counter32
    MAX-ACCESS  read-only
    STATUS      current
    DESCRIPTION
         ""
    ::= { ipuMGCPMsgStatsEntry 7 }

ipuMGCPFailedCmdsSent OBJECT-TYPE
    SYNTAX      Counter32
    MAX-ACCESS  read-only
    STATUS      current
    DESCRIPTION
         ""
    ::= { ipuMGCPMsgStatsEntry 8 }

ipuMGCPSuccessResponsesSent OBJECT-TYPE
    SYNTAX      Counter32
    MAX-ACCESS  read-only
    STATUS      current
    DESCRIPTION
         ""
    ::= { ipuMGCPMsgStatsEntry 9 }

ipuMGCPSuccessResponsesReceived OBJECT-TYPE
    SYNTAX      Counter32
    MAX-ACCESS  read-only
    STATUS      current
    DESCRIPTION
         ""
    ::= { ipuMGCPMsgStatsEntry 10 }

ipuMGCPRetranResponsesSent OBJECT-TYPE
    SYNTAX      Counter32
    MAX-ACCESS  read-only
    STATUS      current
    DESCRIPTION
         ""
    ::= { ipuMGCPMsgStatsEntry 11 }

ipuMGCPRetranResponsesReceived OBJECT-TYPE
    SYNTAX      Counter32
    MAX-ACCESS  read-only
    STATUS      current
    DESCRIPTION
         ""
    ::= { ipuMGCPMsgStatsEntry 12 }

ipuMGCPBadformatResponsesReceived OBJECT-TYPE
    SYNTAX      Counter32
    MAX-ACCESS  read-only
    STATUS      current
    DESCRIPTION
         ""
    ::= { ipuMGCPMsgStatsEntry 13 }

-- asSysTables group
-- asNodeTable

asNodeTable OBJECT-TYPE
    SYNTAX     SEQUENCE OF AsNodeEntry   
    MAX-ACCESS not-accessible   
    STATUS     current   
    DESCRIPTION   
         "This table contains the node information for each node in the
	  Application server Cluster."
    ::= { asSysTables 1 }   
   
asNodeEntry OBJECT-TYPE   
    SYNTAX     AsNodeEntry
    MAX-ACCESS not-accessible   
    STATUS     current   
    DESCRIPTION   
         "Entry contains information about a single node."
    INDEX { asNodeId }   
    ::= { asNodeTable 1}

AsNodeEntry ::=   
    SEQUENCE {  
          asNodeId                          Integer32,
          asNodeName                        DisplayString,
          asNodeRole                        INTEGER,
	  asNodeCCFlag			    INTEGER,
          asNodeOperStatus                  INTEGER,
          asNodeAdminStatus                 INTEGER
    } 

asNodeId OBJECT-TYPE
    SYNTAX      Integer32 (0 | 1..10)
    MAX-ACCESS  not-accessible
    STATUS      current
    DESCRIPTION
        "App server node Id. If node id is 0 it means node is a stand-alone node."
    ::= { asNodeEntry 1 }

asNodeName OBJECT-TYPE
    SYNTAX      DisplayString (SIZE (0..50))
    MAX-ACCESS  read-only
    STATUS      current
    DESCRIPTION
        "Name of the Application."
    ::= { asNodeEntry 2 }

asNodeRole OBJECT-TYPE
    SYNTAX      INTEGER {
		    alone (0),
                    captain (1),
                    player (2)
                }
    MAX-ACCESS  read-only
    STATUS      current
    DESCRIPTION
        "Role of the node. At a time only one node will be the captain.
         All other nodes in the cluster will be players. In case of
         stand alone node role value will be alone(0)."
    ::= { asNodeEntry 3 }

asNodeCCFlag OBJECT-TYPE
    SYNTAX      INTEGER {
		    off (0),
                    on (1)
                }
    MAX-ACCESS  read-only
    STATUS      current
    DESCRIPTION
        "This flag give whether the node is a CaptainCapable node or not. There
	 will be two captain capable nodes in an active-active cluster." 
    ::= { asNodeEntry 4 }

asNodeOperStatus OBJECT-TYPE
    SYNTAX      INTEGER {
                    up (1),
                    down (2)
                }
    MAX-ACCESS  read-only
    STATUS      current
    DESCRIPTION
        "The operational status of the node."
    ::= { asNodeEntry 5 }

asNodeAdminStatus OBJECT-TYPE
    SYNTAX      INTEGER {
		    locked (1),
		    unlocked (2)
		}
    MAX-ACCESS  read-only
    STATUS      current
    DESCRIPTION
        "Administration status of the node."
    ::= { asNodeEntry 6 }


-- Objects for framework configuration

fcOverloadInterval OBJECT-TYPE
    SYNTAX      Integer32(10..100)
    UNITS	"Sec"
    MAX-ACCESS  read-write
    STATUS      current
    DESCRIPTION
         "Interval value in seconds. Framework checks for the load for every
          interval and takes necessary actions if overload protection threshold
          values exceed."
    DEFVAL	{ 20 }
    ::= { frameConfig 1 }

fcOverloadThreshold1 OBJECT-TYPE
    SYNTAX      Integer32
    MAX-ACCESS  read-write
    STATUS      current
    DESCRIPTION
         "First threshold value for the load on the system. Fraework will have
          three threshold values. When first threshold exceeds "
    DEFVAL { 1500 }
    ::= { frameConfig 2 }

fcOverloadThreshold2 OBJECT-TYPE
    SYNTAX      Integer32
    MAX-ACCESS  read-write
    STATUS      current
    DESCRIPTION
         "Second threshold value for the load on the system. Fraework will have
          three threshold values. When second threshold exceeds "
    DEFVAL { 1700 }
    ::= { frameConfig 3 }

fcOverloadThreshold3 OBJECT-TYPE
    SYNTAX      Integer32
    MAX-ACCESS  read-write
    STATUS      current
    DESCRIPTION
         "Third threshold value for the load on the system. Fraework will have
          three threshold values. When third threshold exceeds "
    DEFVAL  { 2000 }
    ::= { frameConfig 4 }

fcCurrentLoad OBJECT-TYPE
    SYNTAX      Integer32
    MAX-ACCESS  read-write
    STATUS      current
    DESCRIPTION
         "Load on the system calculated for the current interval of fcOverloadInterval"
    ::= { frameConfig 5 }


--
-- Objects for UM (Unified Messaging) App
-- 

umOperStatus OBJECT-TYPE
    SYNTAX      INTEGER {
                     up (1),
                     down (2)
                }
    MAX-ACCESS  read-only
    STATUS      current
    DESCRIPTION
         "Operational status of UM application."
    ::= { umScalars 1 }

umAnsweringModeCallsInProgress OBJECT-TYPE
    SYNTAX      Gauge32
    MAX-ACCESS  read-only
    STATUS      current
    DESCRIPTION
         "Number of calls being handled currently in Call Answering Mode 
          by UM."
    ::= { umScalars 2 }

umUIModeCallsInProgress OBJECT-TYPE
    SYNTAX      Gauge32
    MAX-ACCESS  read-only
    STATUS      current
    DESCRIPTION
         "Number of calls being handled currently in User Interface Mode 
          by UM."
    ::= { umScalars 3 }

umMaxCallsSupported OBJECT-TYPE
    SYNTAX      Integer32
    MAX-ACCESS  read-only
    STATUS      current
    DESCRIPTION
         "Maximum number of calls that can be handled concurrently by 
          UM Application."
    ::= { umScalars 4 }

umAnsweringModeCallsCompleted OBJECT-TYPE
    SYNTAX      Counter32
    MAX-ACCESS  read-only
    STATUS      current
    DESCRIPTION
         "Total number of calls completed in Call Answering Mode by UM."
    ::= { umScalars 5 }

umUIModeCallsCompleted OBJECT-TYPE
    SYNTAX      Counter32
    MAX-ACCESS  read-only
    STATUS      current
    DESCRIPTION
         "Total number of calls completed in User Interface Mode by UM."
    ::= { umScalars 6 }

umVoiceMailsSent OBJECT-TYPE
    SYNTAX      Counter32
    MAX-ACCESS  read-only
    STATUS      current
    DESCRIPTION
         "Total number of voice mails sent by UM Application"
    ::= { umScalars 7 }

umEMailsSent OBJECT-TYPE
    SYNTAX      Counter32
    MAX-ACCESS  read-only
    STATUS      obsolete
    DESCRIPTION
         "Total number of e-mails sent by UM Application"
    ::= { umScalars 8 }

umFaxSent OBJECT-TYPE
    SYNTAX      Counter32
    MAX-ACCESS  read-only
    STATUS      current
    DESCRIPTION
         "Total number of FAX messages sent by UM Application"
    ::= { umScalars 9 }

umSentMessagesTotalSize OBJECT-TYPE
    SYNTAX      Counter32
    UNITS       "KB"
    MAX-ACCESS  read-only
    STATUS      current
    DESCRIPTION
         "Total Size of the messages sent in Kilo Bytes. This number is 
          rounded to the nearest integer."
    ::= { umScalars 10 }

umOutboundCallsInProgress OBJECT-TYPE
    SYNTAX      Gauge32
    MAX-ACCESS  read-only
    STATUS      current
    DESCRIPTION
         "Number of outbound calls that are in progress."
    ::= { umScalars 11 }

umOutboundCallsCompleted OBJECT-TYPE
    SYNTAX      Counter32
    MAX-ACCESS  read-only
    STATUS      current
    DESCRIPTION
         "Total number of outbound calls that are completed. "
    ::= { umScalars 12 }

umAutoAttendantCallsInProgress OBJECT-TYPE
    SYNTAX      Gauge32
    MAX-ACCESS  read-only
    STATUS      current
    DESCRIPTION
         "Number of Auto attendant calls that are in progress."
    ::= { umScalars 13 }

umAutoAttendantCallsCompleted OBJECT-TYPE
    SYNTAX      Counter32
    MAX-ACCESS  read-only
    STATUS      current
    DESCRIPTION
         "Total number of Auto Attendant calls that are completed. "
    ::= { umScalars 14 }

umMsgStoreDiskUsage OBJECT-TYPE
    SYNTAX		Gauge32 (0..100)
    MAX-ACCESS	read-only
    STATUS		current
    DESCRIPTION
         "Percentage of disk utilization by UM Application to store the
          messages."
    ::= { umScalars 15 }

umMsgStoreSize OBJECT-TYPE
    SYNTAX		Gauge32
    UNITS		"GB"
    MAX-ACCESS	read-only
    STATUS		current
    DESCRIPTION
         "Total disk space utilized by UM Application to store the 
          messages. This objects gives the memory size in giga bytes."
    ::= { umScalars 16 }

umTrapDescr OBJECT-TYPE
    SYNTAX      DisplayString (SIZE (0..255))
    MAX-ACCESS  accessible-for-notify
    STATUS      current
    DESCRIPTION
         "Description of the latest trap that has been generated by UM 
          Application. This object is used to construct the UM notifications."
    ::= { umScalars 17 }

umOrgTable OBJECT-TYPE
    SYNTAX     SEQUENCE OF UmOrgEntry   
    MAX-ACCESS not-accessible   
    STATUS     current   
    DESCRIPTION   
         "This table contains information for each organization
          supported by the UM application."
    ::= { umTables 1 }   
   
umOrgEntry OBJECT-TYPE   
    SYNTAX     UmOrgEntry
    MAX-ACCESS not-accessible   
    STATUS     current   
    DESCRIPTION   
         "A row of information per orgainization." 
    INDEX { umOrgIndex }   
    ::= { umOrgTable 1}

UmOrgEntry ::=   
    SEQUENCE {  
          umOrgIndex                 Integer32,
          umOrgName                  DisplayString,
          umOrgMsgsDiskUsage         Gauge32,
          umOrgMsgsSize              Gauge32
    }

umOrgIndex OBJECT-TYPE
    SYNTAX		Integer32 (0..2147483647)
    MAX-ACCESS  not-accessible
    STATUS		current
    DESCRIPTION
         "Index for the organization."
    ::= { umOrgEntry 1 }

umOrgName OBJECT-TYPE
    SYNTAX		DisplayString
    MAX-ACCESS  read-only
    STATUS		current
    DESCRIPTION
         "Domain name of the organization."
    ::= { umOrgEntry 2 }

umOrgMsgsDiskUsage OBJECT-TYPE
    SYNTAX		Gauge32 (0..100)
    MAX-ACCESS	read-only
    STATUS		current
    DESCRIPTION
         "Percentage of disk utilization by UM Application to store the
          messages for organization."
    ::= { umOrgEntry 3 }

umOrgMsgsSize OBJECT-TYPE
    SYNTAX		Gauge32
    UNITS		"GB"
    MAX-ACCESS	read-only
    STATUS		current
    DESCRIPTION
         "Total disk space utilized by UM to store the messages for 
          organization . This objects gives the memory size in giga bytes."
    ::= { umOrgEntry 4 }
 
umPagingTaskLastRun OBJECT-TYPE
    SYNTAX      DateAndTime
    MAX-ACCESS  read-only
    STATUS      current
    DESCRIPTION
         "Date and Time at, Paging task of UM ran last time."
    ::= { paging 1 }

umPagesSent OBJECT-TYPE
    SYNTAX      Counter32
    MAX-ACCESS  read-only
    STATUS      current
    DESCRIPTION
         "Total Number of Pages sent by Paging Task of UM."
    ::= { paging 2 }

umPagesPending OBJECT-TYPE
    SYNTAX      Gauge32
    MAX-ACCESS  read-only
    STATUS      current
    DESCRIPTION
         "Total Number of Pages that are pending for delivery by Paging 
          Task of UM."
    ::= { paging 3 }

umMWNTaskLastRun OBJECT-TYPE
    SYNTAX      DateAndTime
    MAX-ACCESS  read-only
    STATUS      current
    DESCRIPTION
         "Date and Time at, MWN (Message Wait Notification) task of UM ran 
          last time."
    ::= { msgWait 1 }

umMWNOutcallsSuccess OBJECT-TYPE
    SYNTAX      Counter32
    MAX-ACCESS  read-only
    STATUS      current
    DESCRIPTION
         "Total number of out calls that are done success by MWN task."
    ::= { msgWait 2 }

umMWNOutcallsFailed OBJECT-TYPE
    SYNTAX      Counter32
    MAX-ACCESS  read-only
    STATUS      current
    DESCRIPTION
         "Total number of out calls done by MWN task and that are failed."
    ::= { msgWait 3 }

umMWNOutcallsPending OBJECT-TYPE
    SYNTAX      Gauge32
    MAX-ACCESS  read-only
    STATUS      current
    DESCRIPTION
         "Total number of MWN task out calls that are pending."
    ::= { msgWait 4 }

umMWITaskLastRun OBJECT-TYPE
    SYNTAX      DateAndTime
    MAX-ACCESS  read-only
    STATUS      current
    DESCRIPTION
         "Date and Time at, MWI (Message Wait Indication) task of UM ran 
          last time."
    ::= { msgWait 5 }

umMWIEventsSent OBJECT-TYPE
    SYNTAX      Counter32
    MAX-ACCESS  read-only
    STATUS      current
    DESCRIPTION
         "Total number of MWI events sent by UM."
    ::= { msgWait 6 }

umMWIEventsFailed OBJECT-TYPE
    SYNTAX      Counter32
    MAX-ACCESS  read-only
    STATUS      current
    DESCRIPTION
         "Total number of MWI events that can not be delivered by UM."
    ::= { msgWait 7 }

umMWIEventsPending OBJECT-TYPE
    SYNTAX      Gauge32
    MAX-ACCESS  read-only
    STATUS      current
    DESCRIPTION
         "Total number of MWI events that are pending for delivery."
    ::= { msgWait 8 }

umNotificationReceiverOperStatus OBJECT-TYPE
    SYNTAX      INTEGER {
                     up (1),
                     down (2)
                }
    MAX-ACCESS  read-only
    STATUS      current
    DESCRIPTION
         "Operational status of the Notification receiver task of UM."
    ::= { notification 1 }

umNotificationReceiverNumConnections OBJECT-TYPE
    SYNTAX      Integer32 (0..2147483647)
    MAX-ACCESS  read-only
    STATUS      current
    DESCRIPTION
         "Number of the live connections with proxy and notification server."
    ::= { notification 2 }

umNotificationSenderOperStatus OBJECT-TYPE
    SYNTAX      INTEGER {
                     up (1),
                     down (2)
                }
    MAX-ACCESS  read-only
    STATUS      current
    DESCRIPTION
         "Operational status of the Notification sender task of UM."
    ::= { notification 3 }

umNotificationServerConnected OBJECT-TYPE
    SYNTAX      INTEGER {
                     true (1),
                     false (2)
                }        
    MAX-ACCESS  read-only
    STATUS      current
    DESCRIPTION
         "Flag that tells whether the Notification Sender Task is connected 
          to Notification Server or not."
    ::= { notification 4 }

confOutCallsSucceeded OBJECT-TYPE
    SYNTAX      Counter32
    MAX-ACCESS  read-only
    STATUS      current
    DESCRIPTION
         "Total number of Conference Out-calls succeeded since last restart."
    ::= { confScalars 1 }

confOutCallsFailed OBJECT-TYPE
    SYNTAX      Counter32
    MAX-ACCESS  read-only
    STATUS      current
    DESCRIPTION
         "Total number of Conference Out-calls failed since last restart."
    ::= { confScalars 2 }

confRecordingsInProgress OBJECT-TYPE
    SYNTAX      Integer32
    MAX-ACCESS  read-only
    STATUS      current
    DESCRIPTION
         "Total number of Conferences currently being recorded."
    ::= { confScalars 3 }

confRecordingsSucceeded OBJECT-TYPE
    SYNTAX      Counter32
    MAX-ACCESS  read-only
    STATUS      current
    DESCRIPTION
         "Total number of Conference recordings that are succeeded."
    ::= { confScalars 4 }

confRecordingsFailed OBJECT-TYPE
    SYNTAX      Counter32
    MAX-ACCESS  read-only
    STATUS      current
    DESCRIPTION
         "Total number of Conference recordings that are failed."
    ::= { confScalars 5 }

confTUILoginsSucceeded OBJECT-TYPE
    SYNTAX      Counter32
    MAX-ACCESS  read-only
    STATUS      current
    DESCRIPTION
         "Total number of Conference TUI Logins that are succeeded."
    ::= { confScalars 6 }

confTUILoginsFailed OBJECT-TYPE
    SYNTAX      Counter32
    MAX-ACCESS  read-only
    STATUS      current
    DESCRIPTION
         "Total number of Conference TUI Logins that are failed."
    ::= { confScalars 7 }

confRecordingsStorageUsage OBJECT-TYPE
    SYNTAX      Integer32 (0..100)
    MAX-ACCESS  read-only
    STATUS      current
    DESCRIPTION
         "Percentage of the Conference recordings storage quota used."
    ::= { confScalars 8 }

confRecordingsStorageAvail OBJECT-TYPE
    SYNTAX      Integer32 
    UNITS	"KB"
    MAX-ACCESS  read-only
    STATUS      current
    DESCRIPTION
         "Storage size available for Conference recordings on the Conference
          Bridge Application Server. This value is in Kbytes."
    ::= { confScalars 9 }

confSlideStorageUsage OBJECT-TYPE
    SYNTAX      Integer32 (0..100)
    MAX-ACCESS  read-only
    STATUS      current
    DESCRIPTION
         "Percentage of the slide storage quota used on the Conference
          Bridge Application Server."
    ::= { confScalars 10 }

confSlideStorageAvail OBJECT-TYPE
    SYNTAX      Integer32 
    UNITS	"KB"
    MAX-ACCESS  read-only
    STATUS      current
    DESCRIPTION
         "Storage size available for slides on the Conference Bridge 
          Application Server. This value is in Kbytes."
    ::= { confScalars 11 }

confInProgress OBJECT-TYPE
    SYNTAX      Integer32 
    MAX-ACCESS  read-only
    STATUS      current
    DESCRIPTION
         "The total number of active conferences on the Conference
          Bridge Application Server."
    ::= { confScalars 12 }

confReservedInUse OBJECT-TYPE
    SYNTAX      Integer32 
    MAX-ACCESS  read-only
    STATUS      current
    DESCRIPTION
         "The total number of reserved conferences that are currently being
          used on the Conference Bridge Application Server."
    ::= { confScalars 13 }

confReservedAvail OBJECT-TYPE
    SYNTAX      Integer32 
    MAX-ACCESS  read-only
    STATUS      current
    DESCRIPTION
         "The total number of reserved conferences that are currently available
          on the Conference Bridge Application Server."
    ::= { confScalars 14 }

confAdhocInUse OBJECT-TYPE
    SYNTAX      Integer32 
    MAX-ACCESS  read-only
    STATUS      current
    DESCRIPTION
         "The total number of adhoc conferences that are currently being
          used on the Conference Bridge Application Server."
    ::= { confScalars 15 }

confActiveParticipants OBJECT-TYPE
    SYNTAX      Integer32 
    MAX-ACCESS  read-only
    STATUS      current
    DESCRIPTION
         "The total number of active participants on the Conference Bridge 
          Application Server."
    ::= { confScalars 16 }

confAPLegsAvail OBJECT-TYPE
    SYNTAX      Integer32 
    MAX-ACCESS  read-only
    STATUS      current
    DESCRIPTION
         "The total number of Active Participant legs available on the 
          Conference Bridge Application Server."
    ::= { confScalars 17 }

confPassiveParticipants OBJECT-TYPE
    SYNTAX      Integer32 
    MAX-ACCESS  read-only
    STATUS      current
    DESCRIPTION
         "The total number of passive participants on the Conference Bridge 
          Application Server."
    ::= { confScalars 18 }

confPPLegsAvail OBJECT-TYPE
    SYNTAX      Integer32 
    MAX-ACCESS  read-only
    STATUS      current
    DESCRIPTION
         "The total number of Passive Participant legs available on the 
          Conference Bridge Application Server."
    ::= { confScalars 19 }

confAdhocParticipants OBJECT-TYPE
    SYNTAX      Integer32 
    MAX-ACCESS  read-only
    STATUS      current
    DESCRIPTION
         "The total number of adhoc participants on the Conference Bridge 
          Application Server."
    ::= { confScalars 20 }

confTrapDescr OBJECT-TYPE
    SYNTAX      DisplayString (SIZE (0..255))
    MAX-ACCESS  accessible-for-notify
    STATUS      current
    DESCRIPTION
         "Description of the latest trap that has been generated by Conference
          Bridge Application. This object is used to construct the CB
          notifications."
    ::= { confScalars 21 }

--
--
-- Notifications
--

asTraps OBJECT IDENTIFIER ::= { asNotifications 0 }

asDataBaseError NOTIFICATION-TYPE
    OBJECTS {
	asTrapSeverity,
        asTrapInfoString
    }
    STATUS  current
    DESCRIPTION
        "This notification is generated whenever Application Server detects 
        that it is not able to connect to DataBase inorder to get 
        configuration information.
        The object asTrapInfoString gives the detailed description of the error
        occured."
    ::= { asTraps 1 }

asWrapperCriticalError NOTIFICATION-TYPE
    OBJECTS {
	asTrapSeverity,
        asTrapInfoString
    }
    STATUS current
    DESCRIPTION
        "This notification is generated whenever the Wrapper program in application 
        server detects a Critical error.
        asTrapInfoString gives the detailed description of the error."
    ::= { asTraps 3 }

asProcMgrCriticalError NOTIFICATION-TYPE
    OBJECTS {
	asTrapSeverity,
        asTrapInfoString
    }
    STATUS current
    DESCRIPTION
        "This notification is generated whenever the Process Manager of application 
        server detects a Critical error.
        asTrapInfoString gives the detailed description of the error."
    ::= { asTraps 4 }

asOverloadThreshold1Exceed NOTIFICATION-TYPE
    OBJECTS {
	asTrapSeverity,
	fcOverloadThreshold1,
	fcCurrentLoad,
        asTrapInfoString
    }
    STATUS current
    DESCRIPTION
        "This notification is generated whenever the framework detects that the load
        for the current interval exceeds the threshold value fcOverloadThreshold1."
    ::= { asTraps 5 }

asOverloadThreshold2Exceed NOTIFICATION-TYPE
    OBJECTS {
	asTrapSeverity,
	fcOverloadThreshold2,
	fcCurrentLoad,
        asTrapInfoString
    }
    STATUS current
    DESCRIPTION
        "This notification is generated whenever the framework detects that the load
        for the current interval exceeds the threshold value fcOverloadThreshold2."
    ::= { asTraps 6 }

asOverloadThreshold3Exceed NOTIFICATION-TYPE
    OBJECTS {
	asTrapSeverity,
	fcOverloadThreshold3,
	fcCurrentLoad,
        asTrapInfoString
    }
    STATUS current
    DESCRIPTION
        "This notification is generated whenever the framework detects that the load
        for the current interval exceeds the threshold value fcOverloadThreshold3."
    ::= { asTraps 7 }

asNoDiskSpace NOTIFICATION-TYPE
    OBJECTS {
        asTrapSeverity,
        asTrapInfoString
    }
    STATUS  current
    DESCRIPTION
        "This notification is generated by Application Server while monitoring
        the disk space and finds disk space is less. asTrapInfoString gives
        the detail description of the disk path and freespace left etc.,"
    ::= { asTraps 8 }
    
asSnmpAgentDown NOTIFICATION-TYPE
    OBJECTS {
        asTrapSeverity,
        asTrapInfoString
    }
    STATUS  current
    DESCRIPTION
        "This notification is generated whenever Application Server detects 
        that the Master SNMP Agent is down."
    ::= { asTraps 9 }
        
asHeartBeatSWDown NOTIFICATION-TYPE
    OBJECTS {
        asTrapSeverity,
        asTrapInfoString
    }
    STATUS  current
    DESCRIPTION
        "This notification is generated whenever Application Server detects 
        that its heart beat software is down or not functioning."
    ::= { asTraps 10 }        

asFipIfDown NOTIFICATION-TYPE
    OBJECTS {
        asTrapSeverity,
        asTrapInfoString
    }
    STATUS  current
    DESCRIPTION
        "This notification is generated whenever Application Server detects 
        that FIP interface is down."
    ::= { asTraps 11 }    

asFwJVMOutOfMemory     NOTIFICATION-TYPE
    OBJECTS {
        asTrapSeverity,
        asTrapInfoString
    }
    STATUS current
    DESCRIPTION
        "This notification is generated whenever the framework process JVM exceeds the 
         critical level of memory usage.
        asTrapInfoString gives the detailed description of the error."
    ::= { asTraps 12 }

asUserPwdExpireWarn     NOTIFICATION-TYPE
    OBJECTS {
        asTrapSeverity,
        asTrapInfoString
    }
    STATUS current
    DESCRIPTION
        "This notification is sent when the application server finds an user's password is 
         going to expire. This is a minor trap. asTrapInfoString gives the user name and in
         howmany days the password expires."
    ::= { asTraps 13 }

asUserPwdExpired     NOTIFICATION-TYPE
    OBJECTS {
        asTrapSeverity,
        asTrapInfoString
    }
    STATUS current
    DESCRIPTION
        "This notification is sent when the application server finds an user's password is 
         expired. This is a major trap. asTrapInfoString gives the user name."
    ::= { asTraps 14 }

asMediaServerDown NOTIFICATION-TYPE
    OBJECTS {
        asTrapSeverity,
        asTrapInfoString
    }
    STATUS  current
    DESCRIPTION
        "This notification is generated whenever Application Server detects 
        that the Media Server it is interacting with is down or not responding."
    ::= { asTraps 100 }

asEJBServerDown NOTIFICATION-TYPE
    OBJECTS {
        asTrapSeverity,
        asTrapInfoString
    }
    STATUS  current
    DESCRIPTION
        "This notification is generated whenever Application Server detects 
        that the EJB Server it is interacting with is down."
    ::= { asTraps 101 }

asTomcatServerDown NOTIFICATION-TYPE
    OBJECTS {
        asTrapSeverity,
        asTrapInfoString
    }
    STATUS  current
    DESCRIPTION
        "This notification is generated whenever Application Server detects 
        that the Tomcat Server it is interacting with is down."
    ::= { asTraps 102 }

asLDAPServerDown NOTIFICATION-TYPE
    OBJECTS {
        asTrapSeverity,
        asTrapInfoString
    }
    STATUS  current
    DESCRIPTION
        "This notification is generated whenever Application Server detects 
        that the LDAP Server it is interacting with is down or not responding.
        asTrapInfoString gives the detailed description."
    ::= { asTraps 103 }

asWebServerDown NOTIFICATION-TYPE
    OBJECTS {
        asTrapSeverity,
        asTrapInfoString
    }
    STATUS  current
    DESCRIPTION
        "This notification is generated whenever Application Server detects 
        that the Web Server is down."
    ::= { asTraps 104 }

asNASServerDown NOTIFICATION-TYPE
    OBJECTS {
        asTrapSeverity
    }
    STATUS  current
    DESCRIPTION
        "This notification is generated whenever Application Server detects 
        that the NAS Server it is using is down."
    ::= { asTraps 105 }

asDataBaseDown NOTIFICATION-TYPE
    OBJECTS {
        asTrapSeverity,
        asTrapInfoString
    }
    STATUS  current
    DESCRIPTION
        "This notification is generated whenever Application Server detects 
        that the database server it is using is down."
    ::= { asTraps 106 }

asVerityAppDown NOTIFICATION-TYPE
    OBJECTS {
        asTrapSeverity
    }
    STATUS  current
    DESCRIPTION
        "This notification is generated whenever Application Server detects 
        that the Verity Application it is using is down."
    ::= { asTraps 107 }

asMessagingServerDown NOTIFICATION-TYPE
    OBJECTS {
        asTrapSeverity,
        asTrapInfoString
    }
    STATUS  current
    DESCRIPTION
        "This notification is generated whenever Application Server detects 
        that the messaging or mailservers are down or not responding. It includes
        imap, pop and smtp servers."
    ::= { asTraps 108 }

asMGCPTimeOut NOTIFICATION-TYPE
    OBJECTS {
        asTrapSeverity
    }
    STATUS current
    DESCRIPTION
        "Timeout of an MGCP Message. Indicates that media Server is not 
        responding."
    ::= { asTraps 109 }

asAppError NOTIFICATION-TYPE
    OBJECTS {
	asTrapSeverity,
        asTrapInfoString
    }
    STATUS current
    DESCRIPTION
        "Notification that indicates the Application Server finds an error
        with the application. An example would be the Application Server
        is not able to initialize the configured application.

        The object asTrapInfoString gives the detailed description of the error
        occured."
    ::= { asTraps 110 }

asNoResources NOTIFICATION-TYPE
    OBJECTS {
        asTrapSeverity
    }
    STATUS current
    DESCRIPTION
        "This notification indicates that Application server is unable to get
        resources allocated on the Media Server."
    ::= { asTraps 111 }

asAppDown NOTIFICATION-TYPE
    OBJECTS {
        asAppName
    }
    STATUS current
    DESCRIPTION
        "This notification is generated whenever the Application's operational
         status changes from up(1) to down(2)."
    ::= { asTraps 112 }

asMGCPDown NOTIFICATION-TYPE
    OBJECTS {
        asTrapSeverity
    }
    STATUS current
    DESCRIPTION
        "This notification is sent when MGCP protocol is down."
    ::= { asTraps 113 }         

asNoAlarmLog NOTIFICATION-TYPE
    OBJECTS {
        asTrapSeverity
    }
    STATUS current
    DESCRIPTION
        "Alarm logs can not be written to non-volatile storage on
         app server."
    ::= { asTraps 114 }

asNoDebugLog NOTIFICATION-TYPE
    OBJECTS {
        asTrapSeverity
    }
    STATUS current
    DESCRIPTION
        "Debug logs can not be written to non-volatile storage on
         app server."
    ::= { asTraps 115 }

asNoCDRLog NOTIFICATION-TYPE
    OBJECTS {
        asTrapSeverity
    }
    STATUS current
    DESCRIPTION
        "Call Detail Record can not be written to non-volatile storage on
         app server."
    ::= { asTraps 116 }

umNotResponding NOTIFICATION-TYPE
    OBJECTS {
	asTrapSeverity,
        umTrapDescr
    }
    STATUS current
    DESCRIPTION
        "This notification is generated by UM Application whenever it 
         detects that it is not getting response from the servers it is
         using.
         These servers include
            LDAP Server
            Mail Server
            TTS Resource Manager
            Network Access Storage (NAS) and so forth.
         Object umTrapDescr object gives the description of the notification."
    ::= { asTraps 117 }

umMajorException NOTIFICATION-TYPE
    OBJECTS {
	asTrapSeverity,
        umTrapDescr
    }
    STATUS current
    DESCRIPTION
        "This notification is generated by UM Application whenever it
         encounters a major exception.
         Object umTrapDescr object gives the detail description of
         the actual notification."
    ::= { asTraps 118 }

asProcessStateChange NOTIFICATION-TYPE
    OBJECTS {
	asTrapSeverity,
        asProcessName,
        asProcessState
    }
    STATUS current
    DESCRIPTION
        "This notification indicates that the state of asProcessName is 
         changed to asProcessState."
    ::= { asTraps 119 }

asProcessManagerDown NOTIFICATION-TYPE
    OBJECTS {
	asTrapSeverity,
        asTrapInfoString
    }
    STATUS current
    DESCRIPTION
        "This notification indicates that the Process Manager on the 
         Application Server is down. Please check the logs for more
         information."
    ::= { asTraps 120 }

asDBTaskError NOTIFICATION-TYPE
    OBJECTS {
	asTrapSeverity,
        asTrapInfoString
    }
    STATUS current
    DESCRIPTION
        "This notification indicates that Cron Tasks on the Application server 
         encountered an error while executing. Please check the logs for more 
         information."
    ::= { asTraps 121 }

asLicensedHardLimitCrossed NOTIFICATION-TYPE
    OBJECTS {
	asTrapSeverity,
        asTrapInfoString
    }
    STATUS  current
    DESCRIPTION
        "This notification is generated whenever Application Server detects
        that the number of calls that are currenlty in progress are crossed the
        licensed hard limit.
        The object asTrapInfoString gives the detailed description of the error
        occured."
    ::= { asTraps 122 }

asSplitBrainDetected NOTIFICATION-TYPE
    OBJECTS {
        asTrapSeverity
    }
    STATUS current
    DESCRIPTION
        "This notification is generated whenever the Wrapper program in application 
         server detects the split brain condition."
    ::= { asTraps 123 }

asNodeDown NOTIFICATION-TYPE
    OBJECTS {
	asTrapSeverity,
        asTrapInfoString
    }
    STATUS current
    DESCRIPTION
        "This notification is generated whenever the Wrapper program in application 
         server detects that a node in the cluster goes down. asTrapInfoString gives
         the details like name of the node that wentdown."
    ::= { asTraps 124 }

asRestartingProcMgr NOTIFICATION-TYPE
    OBJECTS {
	asTrapSeverity,
        asTrapInfoString
    }
    STATUS current
    DESCRIPTION
        "This notification is generated whenever the Wrapper program in application 
         server restarts the process manager of the node. asTrapInfoString gives
         the detailed information and the actual reason for restarting."
    ::= { asTraps 125 }

confMajorException NOTIFICATION-TYPE
    OBJECTS {
	asTrapSeverity,
        confTrapDescr
    }
    STATUS current
    DESCRIPTION
        "This notification is generated by Conference Bridge Application whenever it
         encounters a major exception.
         Object confTrapDescr object gives the detail description of
         the actual notification."
    ::= { asTraps 126 }

asFwJVMHighMemUsage      NOTIFICATION-TYPE
    OBJECTS {
	asTrapSeverity,
        asTrapInfoString
    }
    STATUS current
    DESCRIPTION
        "This notification is generated whenever the framework process JVM reaches the 
         first threshold level of memory usage.
        asTrapInfoString gives the detailed description of the error."
    ::= { asTraps 127 }

asMGCPPktLossCrossed NOTIFICATION-TYPE
    OBJECTS {
        asTrapSeverity
    }
    STATUS current
    DESCRIPTION
        "Notification which specifies that Packet loss is exceeded 
         ipuMGCPHigherBoundForPacketLoss."
    ::= { asTraps 200 }

asMGCPJitterCrossed NOTIFICATION-TYPE
    OBJECTS {
        asTrapSeverity
    }
    STATUS current
    DESCRIPTION
        "Notification which specifies that Jitter is exceeding 
         ipuMGCPHigherBoundForJitter."
    ::= { asTraps 201 }

asMGCPLatencyCrossed NOTIFICATION-TYPE
    OBJECTS {
        asTrapSeverity
    }
    STATUS current
    DESCRIPTION
        "Notification which specifies that Latency is exceeding 
         ipuMGCPHigherBoundForLatency."
    ::= { asTraps 202 }

umMinorException NOTIFICATION-TYPE
    OBJECTS {
	asTrapSeverity,
        umTrapDescr
    }
    STATUS current
    DESCRIPTION
        "This notification is generated by UM Application whenever it
         encounters a minor exception.
         Object umTrapDescr object gives the detail description of
         the actual notification."
    ::= { asTraps 203 }

asCallWithNoApp NOTIFICATION-TYPE
    OBJECTS {
        asTrapSeverity
    }
    STATUS current
    DESCRIPTION
         "Notification generated by frame work whenever it receives
          a call with no Application."	
    ::= { asTraps 204 }

asLicensedSoftLimitCrossed NOTIFICATION-TYPE
    OBJECTS {
	asTrapSeverity,
        asTrapInfoString
    }
    STATUS  current
    DESCRIPTION
        "This notification is generated whenever Application Server detects
        that the number of calls that are currently in progress are crossed the
        licensed soft limit.
        The object asTrapInfoString gives the detailed description of the error
        occured."
    ::= { asTraps 205 }

asProcMgrMinorError NOTIFICATION-TYPE
    OBJECTS {
	asTrapSeverity,
        asTrapInfoString
    }
    STATUS  current
    DESCRIPTION
        "This notification is generated whenever the Process Manager of the 
        Application Server detects a minor error.
        The object asTrapInfoString gives the detailed description of the error
        occured."
    ::= { asTraps 206 }

asWrapperMinorError NOTIFICATION-TYPE
    OBJECTS {
	asTrapSeverity,
        asTrapInfoString
    }
    STATUS  current
    DESCRIPTION
        "This notification is generated whenever the Wrapper program of the 
        Application Server detects a minor error.
        The object asTrapInfoString gives the detailed description of the error
        occured."
    ::= { asTraps 207 }

asDbSwitch NOTIFICATION-TYPE
    OBJECTS {
	asTrapSeverity,
        asTrapInfoString
    }
    STATUS obsolete
    DESCRIPTION
        "This notification is generated whenever the DB is switched from 
        PRIMARY to SECONDARY or vice-versa.
        The object asTrapInfoString gives the detailed description of the error
        occured."
    ::= { asTraps 208 }

confMinorException NOTIFICATION-TYPE
    OBJECTS {
	asTrapSeverity,
        confTrapDescr
    }
    STATUS current
    DESCRIPTION
        "This notification is generated by Conference Bridge Application 
         whenever it encounters a minor exception.
         Object confTrapDescr object gives the detail description of
         the actual notification."
    ::= { asTraps 209 }

asMGCPUp NOTIFICATION-TYPE
    OBJECTS {
        asTrapSeverity
    }
    STATUS current
    DESCRIPTION
        "This notification is sent when the MGCP protocol is up."
    ::= { asTraps 300 }         

asMGCPPktLossFalls NOTIFICATION-TYPE
    OBJECTS {
        asTrapSeverity
    }
    STATUS current
    DESCRIPTION
        "Notification which specifies that Packet loss is below 
         ipuMGCPLowerBoundForPacketLoss."
    ::= { asTraps 301 }

asMGCPJitterFalls NOTIFICATION-TYPE
    OBJECTS {
        asTrapSeverity
    }
    STATUS current
    DESCRIPTION
        "Notification which specifies that Jitter is below 
         ipuMGCPLowerBoundForJitter."
    ::= { asTraps 302 }

asMGCPLatencyFalls NOTIFICATION-TYPE
    OBJECTS {
        asTrapSeverity
    }
    STATUS current
    DESCRIPTION
        "Notification which specifies that Latency is below 
         ipuMGCPLowerBoundForLatency."
    ::= { asTraps 303 }

asAppUp NOTIFICATION-TYPE
    OBJECTS {
	asTrapSeverity,
        asAppName
    }
    STATUS current
    DESCRIPTION
        "Notification that is generated when a Application is up." 
    ::= { asTraps 304 }

asSwitchover NOTIFICATION-TYPE
    OBJECTS {
	asTrapSeverity,
        asMode
    }
    STATUS current
    DESCRIPTION
        "Notification that is generated when the Active and the Standby App 
         Servers are switched over." 
    ::= { asTraps 305 }

asSplitBrainCorrected NOTIFICATION-TYPE
    OBJECTS {
        asTrapSeverity
    }
    STATUS current
    DESCRIPTION
        "This notification is generated whenever the Wrapper program in application 
         server corrects the split brain condition."
    ::= { asTraps 306 }

asBecameCaptain NOTIFICATION-TYPE
    OBJECTS {
        asTrapSeverity
    }
    STATUS current
    DESCRIPTION
        "This notification is generated whenever an appserver node in a cluster
         becomes the Captain of the cluster. This is informational."
    ::= { asTraps 307 }

asNodeUp NOTIFICATION-TYPE
    OBJECTS {
	asTrapSeverity,
        asTrapInfoString
    }
    STATUS current
    DESCRIPTION
        "This notification is generated whenever the Wrapper program in application 
         server detects that the operStatus of a node in the cluster changes to UP.
         asTrapInfoString gives the details like name of the node that wentdown."
    ::= { asTraps 308 }

asHMNotification NOTIFICATION-TYPE
    OBJECTS {
	asTrapSeverity,
        asTrapInfoString
    }
    STATUS current
    DESCRIPTION
        "This notification is generated whenever the health monitoring subsystem in application 
         server detects that a health check has failed.
         asTrapInfoString gives the additional details on why the specific health check failed."
    ::= { asTraps 309 }

asDFNDown NOTIFICATION-TYPE
    OBJECTS {
    asTrapSeverity,
        asTrapInfoString
    }
    STATUS current
    DESCRIPTION
        "This notification is generated whenever the Application Server detects one of its Diameter
         Front Nodes (DFN) as down.
         asTrapInfoString gives the additional details such as the ID of the DFN that went down."
    ::= { asTraps 310 }

asDiameterPeerDown NOTIFICATION-TYPE
    OBJECTS {
    asTrapSeverity,
        asTrapInfoString
    }
    STATUS current
    DESCRIPTION
        "This notification is generated whenever the Application Server detects a Diameter peer
         (HSS / SLF) that it communicates with as down.
         asTrapInfoString gives the additional details such as the name of the Diameter peer that went down."
    ::= { asTraps 311 }

asCRCXFailure NOTIFICATION-TYPE
    OBJECTS {
        asTrapSeverity,
        asTrapInfoString
    }
    STATUS current
    DESCRIPTION
        "This notification is generated whenever a CRCX fails "
    ::= { asTraps 312 }

asCallCollectorAction NOTIFICATION-TYPE
    OBJECTS {
        asTrapSeverity,
        asTrapInfoString
    }
    STATUS current
    DESCRIPTION
        "This notification is generated whenever call reclamation happens "
    ::= { asTraps 313 }
    
END
